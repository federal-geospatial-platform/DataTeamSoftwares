FME workspace Produire_InsertInto_Evaluation.fmw

Parameters:
- IN_XLS_CONFIG_FILE = $(FME_MF_DIR)Quality Indicators Mapping.xlsx
- SourceDataset_XLSXR = C:\Users\ngariepy\Documents\GitHub\source_quality\FoundationLayers\*.xlsx   # Source Microsoft Excel File(s)
- DestDataset_TEXTLINE = $(FME_MF_DIR)INSERT_ASSESSMENTS.sql   # Destination Text File

Readers:
- XLSXR_1: XLSXR from $(IN_XLS_CONFIG_FILE)
- XLSXR_2: XLSXR from $(SourceDataset_XLSXR)

Writers:
- TEXTLINE_1: TEXTLINE to $(DestDataset_TEXTLINE)

AggrégationConfig (reader XLSXR_1)
    attributes: metadata_uuid char(3), quality_id char(3), assessment_date char(3), version_when_assessed char(3), resources_when_assessed char(3), thumb_present char(4), map_included char(4), thumb_represent_dataset char(4), thumb_comments char(4), extent_dataset char(4), extent_comments char(4), meaningfulness_title_fr char(4), meaningfulness_title_en char(4), date_format_compliant_fr char(4), date_format_compliant_en char(4), scale_format_compliant_fr char(4), scale_format_compliant_en char(4), no_starting_with_fr  char(4), no_starting_with_en char(4), acronyms_defined_fr char(4), acronyms_defined_en char(4), no_org_name_fr char(4), no_org_name_en char(4), title_comments  char(4), meaningfulness_kw char(4), nb_keywords_compliant char(4), no_determinants char(4), nb_topics_compliant char(4), keywords_comments char(4), tbs_openess_fr char(4),
      tbs_openess_en char(4), meaningfulness_ab_fr char(4), meaningfulness_ab_en char(4), abstract_comments  char(4), supdoc_present_fr char(4), supdoc_present_en char(4), supportingdoc_comments char(4), working_links char(4), honest char(4), international char(4), web_service_available  char(4), view_this_map_functional char(4), accessibility_comments char(4), open_fomat_present char(4), open_webservice_present char(4), open_comments char(4), good_resources_name_translation char(4), good_resources_content_translation char(4), resource_comments_translation char(4), good_title_translation char(4), good_keywords_translation char(4), good_abstract_translation  char(4), mandatory_comments_translation char(4), good_legend_translation char(4), good_attributes_translation char(4), map_content_comments_translation char(4), fast_loading_time_fr char(4), fast_loading_time_en char(4), too_many_layers_slow_fr char(4), too_many_layers_slow_en char(4),
      relevant_at_scale_fr char(4), relevant_at_scale_en char(4), mapscaling_comments  char(4), symbols_distinct_fr char(4), symbols_distinct_en char(4), scale_adjusting_fr char(4), scale_adjusting_en char(4), proper_topo_principles_fr char(4), proper_topo_principles_en char(4), categories_related_to_topic_fr char(4), categories_related_to_topic_en char(4), appropriate_geometry_fr char(4), appropriate_geometry_en char(4), mapsymbology_comments char(4), legend_map_consistent_fr char(4), legend_map_consistent_en char(4), legend_viewable_fr char(4), legend_viewable_en char(4), appropriate_legend_fr char(4), appropriate_legend_en char(4), legend_no_acronyms_fr char(4), legend_no_acronyms_en char(4), description_clear_fr char(4), description_clear_en char(4), legend_comments char(4), attributes_present_fr char(4), attributes_present_en char(4), understandable_attributes_fr  char(4), understandable_attributes_en char(4), featureattandvalues_comments char(4),
      metadata_hnap_compliant char(4), hnap_comments  char(4), CO string
    -> AttributeExploder_2
AttributeCreator
    ATTR_TABLE:
      SET_TO text_line_data = INSERT INTO public.quality_assessments(	metadata_uuid, quality_id, assessment_date, version_when_assessed, resources_when_assessed, thumb_present, map_included, thumb_represent_dataset, thumb_comments, extent_dataset, extent_comments, meaningfulness_title_fr, meaningfulness_title_en, date_format_compliant_fr, date_format_compliant_en, scale_format_compliant_fr, scale_format_compliant_en, no_starting_with_fr, no_starting_with_en, acronyms_defined_fr, acronyms_defined_en, no_org_name_fr, no_org_name_en, title_comments, meaningfulness_kw, nb_keywords_compliant, no_determinants, nb_topics_compliant, keywords_comments, tbs_openess_fr, tbs_openess_en, meaningfulness_ab_fr, meaningfulness_ab_en, abstract_comments, supdoc_present_fr, supdoc_present_en, supportingdoc_comments, working_links, honest, international, web_service_available, view_this_map_functional, accessibility_comments, open_fomat_present, open_webservice_present, open_comments, good_resources_name_translation, good_resources_content_translation, resource_comments_translation, good_title_translation, good_keywords_translation, good_abstract_translation, mandatory_comments_translation, good_legend_translation, good_attributes_translation, map_content_comments_translation, fast_loading_time_fr, fast_loading_time_en, too_many_layers_slow_fr, too_many_layers_slow_en, relevant_at_scale_fr, relevant_at_scale_en, mapscaling_comments, symbols_distinct_fr, symbols_distinct_en, scale_adjusting_fr, scale_adjusting_en, proper_topo_principles_fr, proper_topo_principles_en, categories_related_to_topic_fr, categories_related_to_topic_en, appropriate_geometry_fr, appropriate_geometry_en, mapsymbology_comments, legend_map_consistent_fr, legend_map_consistent_en, legend_viewable_fr, legend_viewable_en, appropriate_legend_fr, appropriate_legend_en, legend_no_acronyms_fr, legend_no_acronyms_en, description_clear_fr, description_clear_en, legend_comments, attributes_present_fr, attributes_present_en, understandable_attributes_fr, understandable_attributes_en, featureattandvalues_comments, metadata_hnap_compliant, hnap_comments)
        	VALUES ('@Value(metadata_uuid)', @Value(quality_id), '@Value(assessment_date)', '@Value(version_when_assessed)', '@Value(resources_when_assessed)', '@Value(thumb_present)', '@Value(map_included)', '@Value(thumb_represent_dataset)', '@Value(thumb_comments)', '@Value(extent_dataset)', '@Value(extent_comments)', '@Value(meaningfulness_title_fr)', '@Value(meaningfulness_title_en)', '@Value(date_format_compliant_fr)', '@Value(date_format_compliant_en)', '@Value(scale_format_compliant_fr)', '@Value(scale_format_compliant_en)', '@Value(no_starting_with_fr)', '@Value(no_starting_with_en)', '@Value(acronyms_defined_fr)', '@Value(acronyms_defined_en)', '@Value(no_org_name_fr)', '@Value(no_org_name_en)', '@Value(title_comments)', '@Value(meaningfulness_kw)', '@Value(nb_keywords_compliant)', '@Value(no_determinants)', '@Value(nb_topics_compliant)', '@Value(keywords_comments)', '@Value(tbs_openess_fr)', '@Value(tbs_openess_en)', '@Value(meaningfulness_ab_fr)', '@Value(meaningfulness_ab_en)', '@Value(abstract_comments)', '@Value(supdoc_present_fr)', '@Value(supdoc_present_en)', '@Value(supportingdoc_comments)', '@Value(working_links)', '@Value(honest)', '@Value(international)', '@Value(web_service_available)', '@Value(view_this_map_functional)', '@Value(accessibility_comments)', '@Value(open_fomat_present)', '@Value(open_webservice_present)', '@Value(open_comments)', '@Value(good_resources_name_translation)', '@Value(good_resources_content_translation)', '@Value(resource_comments_translation)', '@Value(good_title_translation)', '@Value(good_keywords_translation)', '@Value(good_abstract_translation)', '@Value(mandatory_comments_translation)', '@Value(good_legend_translation)', '@Value(good_attributes_translation)', '@Value(map_content_comments_translation)', '@Value(fast_loading_time_fr)', '@Value(fast_loading_time_en)', '@Value(too_many_layers_slow_fr)', '@Value(too_many_layers_slow_en)', '@Value(relevant_at_scale_fr)', '@Value(relevant_at_scale_en)', '@Value(mapscaling_comments)', '@Value(symbols_distinct_fr)', '@Value(symbols_distinct_en)', '@Value(scale_adjusting_fr)', '@Value(scale_adjusting_en)', '@Value(proper_topo_principles_fr)', '@Value(proper_topo_principles_en)', '@Value(categories_related_to_topic_fr)', '@Value(categories_related_to_topic_en)', '@Value(appropriate_geometry_fr)', '@Value(appropriate_geometry_en)', '@Value(mapsymbology_comments)', '@Value(legend_map_consistent_fr)', '@Value(legend_map_consistent_en)', '@Value(legend_viewable_fr)', '@Value(legend_viewable_en)', '@Value(appropriate_legend_fr)', '@Value(appropriate_legend_en)', '@Value(legend_no_acronyms_fr)', '@Value(legend_no_acronyms_en)', '@Value(description_clear_fr)', '@Value(description_clear_en)', '@Value(legend_comments)', '@Value(attributes_present_fr)', '@Value(attributes_present_en)', '@Value(understandable_attributes_fr)', '@Value(understandable_attributes_en)', '@Value(featureattandvalues_comments)', '@Value(metadata_hnap_compliant)', '@Value(hnap_comments)');
    -> text_line (writer TEXTLINE_1)
text_line (writer TEXTLINE_1)
    attributes: text_line_data buffer

Bookmark: Lecture du fichier excel sans tenir compte de l'entete
New Indicators (reader XLSXR_2)
    attributes: A char(83), B char(83), C char(83), D char(364), E char(120), F char(83), G char(470), H char(739), I char(40), J char(40), K char(40), L char(31)
    -> DuplicateFilter_4
    -> AttributeExposer_2
AttributeExposer_2
    ATTR_LIST = xlsx_row_id,E,F
    -> StringReplacer
StringReplacer
    CASE = NO
    FIND_TEXT = "
    NO_MATCH = _FME_NO_OP_
    REGEXP = NO
    REPLACE_TEXT = --
    SRC_ATTRS = E,F
    -> StringReplacer_2
StringReplacer_2
    CASE = NO
    FIND_TEXT = '
    NO_MATCH = _FME_NO_OP_
    REGEXP = NO
    REPLACE_TEXT = ''
    SRC_ATTRS = E,F
    -> StringReplacer_3
StringReplacer_3
    CASE = NO
    FIND_TEXT = Not Applicable
    NO_MATCH = _FME_NO_OP_
    REGEXP = NO
    REPLACE_TEXT = NA
    SRC_ATTRS = E,F
    -> StringReplacer_4
StringReplacer_4
    CASE = NO
    FIND_TEXT = Not Applicable
    NO_MATCH = _FME_NO_OP_
    REGEXP = NO
    REPLACE_TEXT = NA
    SRC_ATTRS = E,F
    -> AttributeKeeper_2
AttributeKeeper_2
    KEEP_ATTRS = E,F,fme_dataset,xlsx_row_id
    -> AttributeCreator_5
AttributeCreator_5
    ATTR_TABLE:
      SET_TO E@Value(xlsx_row_id) = @Value(E)
      SET_TO F@Value(xlsx_row_id) = @Value(F)
    -> AttributeRemover
AttributeRemover
    REMOVE_ATTRS = H,A,F,G,I,B,D,xlsx_row_id,C,J,E
    -> FeatureMerger_2 [SUPPLIER]
DuplicateFilter_4
    INPUT_ORDERED_CHOICE = No
    KEYATTR = fme_dataset
    UNIQUE -> AttributeKeeper_3
AttributeKeeper_3
    KEEP_ATTRS = fme_dataset
    -> FeatureMerger_2 [REQUESTOR]
FeatureMerger_2
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(fme_dataset) @Value(fme_dataset) AUTO
    MERGE_TYPE = Attributes Only
    PROCESS_DUPS = YES
    REJECT_NULL_MISSING_KEYS = No
    SUPPLIERS_FIRST = No
    MERGED -> AttributeCreator_6
AttributeCreator_6
    ATTR_TABLE = SET_TO _ordre = 2
    -> Sorter_3

Bookmark: Création des attributs selon le modèle dénormalisé en fonction du fichier de configuration
Note: Le fichier de configuration indique quelle cellule contient l'information pour l'attribut en question,
AttributeExploder_2
    ATTR_NAME_LABEL = _attr_name
    ATTR_VALUE_LABEL = _attr_value
    EXPLODING_TYPE = Features
    KEEP_ATTRIBUTES = No
    KEEP_GEOMETRY = No
    -> Tester_3
Tester_3
    BOOL_OP = AND
    COMPOSITE_TEST = 1 AND 2 AND 3 AND 4
    TEST_CLAUSE:
      CASE_INSENSITIVE_TEST @Value(_attr_name) NOT_BEGINS_WITH fme
      CASE_INSENSITIVE_TEST @Value(_attr_name) NOT_BEGINS_WITH multi
      CASE_INSENSITIVE_TEST @Value(_attr_name) NOT_BEGINS_WITH xlsx
      CASE_INSENSITIVE_TEST @Value(_attr_value) NOT_= ?
    TEST_MODE = CASE_INSENSITIVE_TEST
    PASSED -> AttributeCreator_7
AttributeCreator_7
    ATTR_TABLE = SET_TO _ordre = 1
    -> Sorter_3
Sorter_3
    SORT_PARM = _ordre NUMERIC ASCENDING
    SORTED -> PythonCaller
PythonCaller
    NEW_ATTRIBUTES = metadata_uuid assessment_date version_when_assessed quality_id resources_when_assessed
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              self.config=[]

          def input(self,feature):
              if int( feature.getAttribute('_ordre'))==1:
                  self.config.append([feature.getAttribute('_attr_name'),feature.getAttribute('_attr_value')])
              else:

                  for elem in self.config:

                      feature.setAttribute(elem[0],feature.getAttribute(elem[1]))

                  self.pyoutput(feature)
          def close(self):
              pass
    PYTHONSYMBOL = FeatureProcessor
    -> AttributeCreator
