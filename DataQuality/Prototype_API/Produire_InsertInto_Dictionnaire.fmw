FME workspace Produire_InsertInto_Dictionnaire.fmw

Parameters:
- SourceDataset_XLSXR = $(FME_MF_DIR)Quality Indicators Mapping.xlsx   # Source Microsoft Excel File(s)
- DestDataset_TEXTLINE = $(FME_MF_DIR)INSERT_DICTIONNARY.sql   # Destination Text File

Readers:
- XLSXR_1: XLSXR from $(SourceDataset_XLSXR)

Writers:
- TEXTLINE_1: TEXTLINE to $(DestDataset_TEXTLINE)

Dictionnary (reader XLSXR_1)
    attributes: indicator_variable_code char(35), indicator_variable_fr char(203), indicator_variable_en char(164), indicator_code char(12), indicator_fr char(36), indicator_en char(30), sub_indicator_code char(20), sub_indicator_fr char(38), sub_indicator_en char(35)
    -> Tester
Tester
    BOOL_OP = OR
    COMPOSITE_TEST = 1
    TEST_CLAUSE = TEST @Value(indicator_variable_code) != ""
    TEST_MODE = TEST
    PASSED -> StringReplacer
StringReplacer
    CASE = NO
    FIND_TEXT = '
    NO_MATCH = _FME_NO_OP_
    REGEXP = NO
    REPLACE_TEXT = ''
    SRC_ATTRS = indicator_en,indicator_variable_en,sub_indicator_code,sub_indicator_en,sub_indicator_fr,indicator_code,indicator_variable_code,indicator_fr,indicator_variable_fr
    -> AttributeCreator
AttributeCreator
    ATTR_TABLE:
      SET_TO text_line_data = INSERT INTO public.dictionnary(
        	indicator_variable_code, indicator_variable_fr, indicator_variable_en, indicator_code, indicator_fr, indicator_en, sub_indicator_code, sub_indicator_fr, sub_indicator_en)
        	VALUES ('@Value(indicator_variable_code)', '@Value(indicator_variable_fr)', '@Value(indicator_variable_en)', '@Value(indicator_code)', '@Value(indicator_fr)', '@Value(indicator_en)', '@Value(sub_indicator_code)', '@Value(sub_indicator_fr)', '@Value(sub_indicator_en)');
    -> text_line (writer TEXTLINE_1)
text_line (writer TEXTLINE_1)
    attributes: text_line_data buffer
