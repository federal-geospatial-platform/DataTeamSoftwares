FME workspace ApprovePublication.fmw

Parameters:
- ENV = TEST
- AUTH_USERNAME =
- AUTH_PASSWORD =

Creator_2
    GEOMTYPE = Geometry Object
    NUM = 1
    CREATED -> AttributeCreator_2
Note: Attendre toutes les exécutions
FeatureHolder
    -> Sampler
Note: Une seule entité
Sampler
    RATE = 1
    SAMPLE_MODE = No
    SAMPLE_TYPE_LONG = First N Features
    SAMPLED -> AttributeKeeper

Bookmark: Sélection de l'environnement
AttributeCreator_2
    ATTR_TABLE = SET_TO env = $(ENV)
    -> AttributeFilter
AttributeFilter
    ATTR_NAME = env
    ATTR_VALUES = <Empty>,<Missing>,<Null>,<Unfiltered>,PROD,STAGING,TEST
    PROD -> AttributeCreator_5
    STAGING -> AttributeCreator_4
    TEST -> AttributeCreator_6
AttributeCreator_5
    ATTR_TABLE = SET_TO _root = https://gcgeo.gc.ca
    -> HTTPCaller_2
AttributeCreator_4
    ATTR_TABLE = SET_TO _root = https://staging.gcgeo.gc.ca
    -> HTTPCaller_2
AttributeCreator_6
    ATTR_TABLE = SET_TO _root = https://test.gcgeo.gc.ca
    -> HTTPCaller_2

Bookmark: Fausse requete pour avoir un XSRF token
Note: Request Post bidon pour obtenir CSRF Token / La requête va planter mais on extrait le Token dans les cookies. La connection restera active et on utilisera la session après. / Voir doc GeoNetwork / https://geonetwork-opensource.org/manuals/trunk/en/customizing-application/misc.html#example-of-csrf-call-using-curl
HTTPCaller_2
    AUTH_METHOD = Basic
    AUTH_PASSWORD = $(AUTH_PASSWORD)
    AUTH_USERNAME = $(AUTH_USERNAME)
    CONNECTION_TIMEOUT_LENGTH = 60
    CUSTOM_HEADERS = Accept;text/html,application/xhtml+xml,application/xml;q=0.9,image/webp,*/*;q=0.8 Cookie;X-XSRF-TOKEN X-XSRF-TOKEN;8696ced3-704d-46a0-b8a0-60f5e66542fc Connection;keep-alive
    ERROR_ATTR = _error
    FOLLOW_REDIRECTS = No
    HTTP_METHOD = POST
    RESPONSE_HEADER_LIST_ATTR = List_header
    SAVE_FILE = Attribute
    STATUS_CODE_ATTR = _http_status_code
    TARGET_ATTR = _response_body
    TARGET_ATTR_ENCODING = auto-detect
    TARGET_URL = @Value(_root)/geonetwork/srv/api/records
    TRANSFER_TIMEOUT_LENGTH = 90
    UPLOAD_CONTENT_TYPE = Text (text/plain)
    UPLOAD_TYPE = Specify Upload Body
    USE_COOKIES = Yes
    VERIFY_SSL_CERTIFICATES = No
    <REJECTED> -> ListSearcher
ListSearcher
    ATTR_VALUE = XSRF-TOKEN
    INDEX_ATTR = _list_index
    LIST_ATTR = List_header{}.value
    MATCHTYPE = REGULAR_EXPRESSION_ENCODED
    PREFIX = _xsrf_token
    FOUND -> AttributeSplitter
AttributeSplitter
    ATTR_NAME = _xsrf_tokenvalue
    DELIMITER = ;
    DROP_EMPTY_PARTS = No
    LIST_NAME = _list
    TRIM_OPTION = Both
    -> AttributeCreator_7
AttributeCreator_7
    ATTR_TABLE = SET_TO _token = @Value(_list{0})
    -> AttributeTrimmer
AttributeTrimmer
    SRC_ATTRS = _token
    TRIM_CHARS = XSRF-TOKEN=
    TRIM_TO_NONE = Yes
    TRIM_TYPE = Left
    -> HTTPCaller

Bookmark: Extraction des requetes de publications en attente
HTTPCaller
    AUTH_METHOD = Basic
    AUTH_PASSWORD = $(AUTH_PASSWORD)
    AUTH_USERNAME = $(AUTH_USERNAME)
    CONNECTION_TIMEOUT_LENGTH = 60
    CUSTOM_HEADERS = Accept;application/json, text/plain, */*
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(_root)/geonetwork/srv/canada/workflow/list/eng
    TRANSFER_TIMEOUT_LENGTH = 90
    USE_COOKIES = No
    VERIFY_SSL_CERTIFICATES = No
    -> JSONFragmenter
JSONFragmenter
    EXPLODE_FORMAT = JSON
    EXTRACT_ATTR = Yes
    JSON_ATTR = _response_body
    JSON_QUERY = json
    READ_FROM_FILE = NO
    RECURSIVE = Yes
    REJECT_EMPTY_LISTS = YES
    FRAGMENTS -> AttributeExploder
    FRAGMENTS -> FeatureMerger [REQUESTOR]
AttributeExploder
    ATTR_NAME_LABEL = _attr_name
    ATTR_VALUE_LABEL = _attr_value
    EXPLODING_TYPE = Features
    KEEP_ATTRIBUTES = No
    KEEP_GEOMETRY = No
    -> Tester_4
Tester_4
    BOOL_OP = COMPOSITE
    COMPOSITE_TEST = 1 AND 2
    TEST_CLAUSE:
      CASE_INSENSITIVE_TEST @Value(_attr_name) ENDS_WITH bulkid
      CASE_INSENSITIVE_TEST @Value(_attr_value) = ""
    TEST_MODE = CASE_INSENSITIVE_TEST
    PASSED -> AttributeCreator_8
AttributeCreator_8
    ATTR_TABLE = SET_TO uuid_list_name = @Value(_attr_name)
    -> StringReplacer
StringReplacer
    CASE = NO
    FIND_TEXT = requestList.nobulkid-
    NO_MATCH = _FME_NO_OP_
    REGEXP = NO
    SRC_ATTRS = uuid_list_name
    -> StringReplacer_2
StringReplacer_2
    CASE = NO
    FIND_TEXT = {0}.bulkid
    NO_MATCH = _FME_NO_OP_
    REGEXP = NO
    SRC_ATTRS = uuid_list_name
    -> FeatureMerger [SUPPLIER]
FeatureMerger
    ATTR_ACCUM_MODE = Merge Supplier
    ATTR_CONFLICT_RES = Use Requestor
    IGNORE_NULLS = No
    JOIN_KEYS = 1 1 AUTO
    LIST_ATTRS_TO_INCLUDE = uuid_list_name
    LIST_NAME = list_nom_liste
    MERGE_TYPE = Attributes Only
    PROCESS_DUPS = NO
    REJECT_NULL_MISSING_KEYS = No
    SUPPLIERS_FIRST = No
    MERGED -> PythonCaller

Bookmark: Extraire du retour les requete de publication de niveau 1
Note: Extraction des entités à approuver
PythonCaller
    NEW_ATTRIBUTES = gl publication_id crl1 processDateLevel1
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              try:
                  #Obtenir la liste des noms de listes
                  liste_nom_liste=feature.getAttribute('list_nom_liste{}.uuid_list_name')

                  for nom_liste in liste_nom_liste:
                      i=0
                      id=feature.getAttribute('requestList.nobulkid-%s{%i}.id'%(nom_liste,i))
                      crl1=feature.getAttribute('requestList.nobulkid-%s{%i}.contentReviewerLevel1.id'%(nom_liste,i))
                      gl=feature.getAttribute('requestList.nobulkid-%s{%i}.group.id'%(nom_liste,i))
                      processDateLevel1=feature.getAttribute('requestList.nobulkid-%s{%i}.processDateLevel1'%(nom_liste,i))

                      token=feature.getAttribute('_token')
                      root=feature.getAttribute('_root')


                      new_feature=fmeobjects.FMEFeature()
                      new_feature.setAttribute('publication_id',id)
                      new_feature.setAttribute('processDateLevel1',processDateLevel1)
                      new_feature.setAttribute('_root',root)
                      new_feature.setAttribute('_token',token)
                      new_feature.setAttribute('crl1',crl1)
                      new_feature.setAttribute('gl',gl)


                      self.pyoutput(new_feature)
              except:
                  raise
          def close(self):
              pass
    PYTHONSYMBOL = FeatureProcessor
    -> Tester
Note: Interval vs external
Tester
    BOOL_OP = OR
    COMPOSITE_TEST = 1
    TEST_CLAUSE = CASE_INSENSITIVE_TEST @Value(gl) = 0
    TEST_MODE = CASE_INSENSITIVE_TEST
    PASSED -> AttributeCreator
    FAILED -> Tester_2
Note: Payload niveau 1 / Premier rang
AttributeCreator
    ATTR_TABLE:
      SET_TO payload = {"type":"approve","requests":[{"id":@Value(publication_id),"comments":"","cr":"@Value(crl1)"}]}
      SET_TO _ordre = 1
    -> Sorter
Note: Only L1 for external workpace
Tester_2
    BOOL_OP = OR
    COMPOSITE_TEST = 1
    TEST_CLAUSE = TEST @Value(processDateLevel1) = ""
    TEST_MODE = TEST
    PASSED -> AttributeCreator_11
    FAILED -> FeatureHolder
Note: Payload niveau 1 / Deuxieme range
AttributeCreator_11
    ATTR_TABLE:
      SET_TO payload = {"type":"approve","requests":[{"id":@Value(publication_id),"comments":"","cr":"@Value(crl1)"}]}
      SET_TO _ordre = 2
    -> Sorter
Note: Tier les données
Sorter
    SORT_PARM = _ordre NUMERIC ASCENDING
    SORTED -> HTTPCaller_3
Note: Exécution requete approbation
HTTPCaller_3
    AUTH_METHOD = Basic
    AUTH_PASSWORD = $(AUTH_PASSWORD)
    AUTH_USERNAME = $(AUTH_USERNAME)
    CONNECTION_TIMEOUT_LENGTH = 60
    CUSTOM_HEADERS = Accept;application/json, text/plain, */* X-XSRF-TOKEN;@Value(_token)
    ERROR_ATTR = _error
    FOLLOW_REDIRECTS = Yes
    HTTP_METHOD = POST
    RESPONSE_HEADER_LIST_ATTR = List_header
    SAVE_FILE = Attribute
    STATUS_CODE_ATTR = _http_status_code
    TARGET_ATTR = _response_body
    TARGET_ATTR_ENCODING = auto-detect
    TARGET_URL = @Value(_root)/geonetwork/srv/canada/workflow/process/eng
    TRANSFER_TIMEOUT_LENGTH = 90
    UPLOAD_BODY = @Value(payload)
    UPLOAD_CONTENT_TYPE = JSON (application/json)
    UPLOAD_TYPE = Specify Upload Body
    USE_COOKIES = Yes
    VERIFY_SSL_CERTIFICATES = No
    -> FeatureHolder
    <REJECTED> -> HTTPCaller_3__Rejected_
HTTPCaller_3__Rejected_: Inspector

Bookmark: Extraction des requetes de publications en attente une seconde fois
AttributeKeeper
    KEEP_ATTRS = _root,_token
    -> HTTPCaller_4
HTTPCaller_4
    AUTH_METHOD = Basic
    AUTH_PASSWORD = $(AUTH_PASSWORD)
    AUTH_USERNAME = $(AUTH_USERNAME)
    CONNECTION_TIMEOUT_LENGTH = 60
    CUSTOM_HEADERS = Accept;application/json, text/plain, */*
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(_root)/geonetwork/srv/canada/workflow/list/eng
    TRANSFER_TIMEOUT_LENGTH = 90
    USE_COOKIES = No
    VERIFY_SSL_CERTIFICATES = No
    -> JSONFragmenter_2
JSONFragmenter_2
    EXPLODE_FORMAT = JSON
    EXTRACT_ATTR = Yes
    JSON_ATTR = _response_body
    JSON_QUERY = json
    READ_FROM_FILE = NO
    RECURSIVE = Yes
    REJECT_EMPTY_LISTS = YES
    FRAGMENTS -> AttributeExploder_2
    FRAGMENTS -> FeatureMerger_2 [REQUESTOR]
AttributeExploder_2
    ATTR_NAME_LABEL = _attr_name
    ATTR_VALUE_LABEL = _attr_value
    EXPLODING_TYPE = Features
    KEEP_ATTRIBUTES = No
    KEEP_GEOMETRY = No
    -> Tester_3
Tester_3
    BOOL_OP = COMPOSITE
    COMPOSITE_TEST = 1 AND 2
    TEST_CLAUSE:
      CASE_INSENSITIVE_TEST @Value(_attr_name) ENDS_WITH bulkid
      CASE_INSENSITIVE_TEST @Value(_attr_value) = ""
    TEST_MODE = CASE_INSENSITIVE_TEST
    PASSED -> AttributeCreator_3
AttributeCreator_3
    ATTR_TABLE = SET_TO uuid_list_name = @Value(_attr_name)
    -> StringReplacer_3
StringReplacer_3
    CASE = NO
    FIND_TEXT = requestList.nobulkid-
    NO_MATCH = _FME_NO_OP_
    REGEXP = NO
    SRC_ATTRS = uuid_list_name
    -> StringReplacer_4
StringReplacer_4
    CASE = NO
    FIND_TEXT = {0}.bulkid
    NO_MATCH = _FME_NO_OP_
    REGEXP = NO
    SRC_ATTRS = uuid_list_name
    -> FeatureMerger_2 [SUPPLIER]
FeatureMerger_2
    ATTR_ACCUM_MODE = Merge Supplier
    ATTR_CONFLICT_RES = Use Requestor
    IGNORE_NULLS = No
    JOIN_KEYS = 1 1 AUTO
    LIST_ATTRS_TO_INCLUDE = uuid_list_name
    LIST_NAME = list_nom_liste
    MERGE_TYPE = Attributes Only
    PROCESS_DUPS = NO
    REJECT_NULL_MISSING_KEYS = No
    SUPPLIERS_FIRST = No
    MERGED -> PythonCaller_2

Bookmark: Approbation niveau 2
Note: Extraction des entités à approuver
PythonCaller_2
    NEW_ATTRIBUTES = gl publication_id crl1 processDateLevel1
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              try:
                  #Obtenir la liste des noms de listes
                  liste_nom_liste=feature.getAttribute('list_nom_liste{}.uuid_list_name')

                  for nom_liste in liste_nom_liste:
                      i=0
                      id=feature.getAttribute('requestList.nobulkid-%s{%i}.id'%(nom_liste,i))
                      crl1=feature.getAttribute('requestList.nobulkid-%s{%i}.contentReviewerLevel1.id'%(nom_liste,i))
                      gl=feature.getAttribute('requestList.nobulkid-%s{%i}.group.id'%(nom_liste,i))
                      processDateLevel1=feature.getAttribute('requestList.nobulkid-%s{%i}.processDateLevel1'%(nom_liste,i))

                      token=feature.getAttribute('_token')
                      root=feature.getAttribute('_root')


                      new_feature=fmeobjects.FMEFeature()
                      new_feature.setAttribute('publication_id',id)
                      new_feature.setAttribute('processDateLevel1',processDateLevel1)
                      new_feature.setAttribute('_root',root)
                      new_feature.setAttribute('_token',token)
                      new_feature.setAttribute('crl1',crl1)
                      new_feature.setAttribute('gl',gl)


                      self.pyoutput(new_feature)
              except:
                  raise
          def close(self):
              pass
    PYTHONSYMBOL = FeatureProcessor
    -> Tester_5
Note: Only L2
Tester_5
    BOOL_OP = OR
    COMPOSITE_TEST = 1
    TEST_CLAUSE = TEST @Value(processDateLevel1) != ""
    TEST_MODE = TEST
    PASSED -> AttributeCreator_10
AttributeCreator_10
    ATTR_TABLE:
      SET_TO payload = {"type":"approve","requests":[{"id":@Value(publication_id),"comments":"","cr":""}]}
      SET_TO _ordre = 3
    -> HTTPCaller_5
HTTPCaller_5
    AUTH_METHOD = Basic
    AUTH_PASSWORD = $(AUTH_PASSWORD)
    AUTH_USERNAME = $(AUTH_USERNAME)
    CONNECTION_TIMEOUT_LENGTH = 60
    CUSTOM_HEADERS = Accept;application/json, text/plain, */* X-XSRF-TOKEN;@Value(_token)
    ERROR_ATTR = _error
    FOLLOW_REDIRECTS = Yes
    HTTP_METHOD = POST
    RESPONSE_HEADER_LIST_ATTR = List_header
    SAVE_FILE = Attribute
    STATUS_CODE_ATTR = _http_status_code
    TARGET_ATTR = _response_body
    TARGET_ATTR_ENCODING = auto-detect
    TARGET_URL = @Value(_root)/geonetwork/srv/canada/workflow/process/eng
    TRANSFER_TIMEOUT_LENGTH = 90
    UPLOAD_BODY = @Value(payload)
    UPLOAD_CONTENT_TYPE = JSON (application/json)
    UPLOAD_TYPE = Specify Upload Body
    USE_COOKIES = Yes
    VERIFY_SSL_CERTIFICATES = No
    -> HTTPCaller_5_Output
    <REJECTED> -> HTTPCaller_5__Rejected_
HTTPCaller_5_Output: Inspector
HTTPCaller_5__Rejected_: Inspector
