FME workspace Upload_metadata.fmw

Parameters:
- WORKSPACE = AB Open Data   # "AB Open Data"%"BC Open Data"%"QC Open Data"%"ON Open Data"%"NB Open Data"%"YT Open Data"%"NS Open Data" WORKSPACE
- IN_XML_DIR =
- ENV =
- AUTH_USERNAME =
- AUTH_PASSWORD =
- PAYLOAD_TEMP_DIR =

Creator
    GEOMTYPE = Geometry Object
    NUM = 1
    CREATED -> AttributeCreator_2
Note: Request Post bidon pour obtenir CSRF Token / La requête va planter mais on extrait le Token dans les cookies. La connection restera active et on utilisera la session après. / Voir doc GeoNetwork / https://geonetwork-opensource.org/manuals/trunk/en/customizing-application/misc.html#example-of-csrf-call-using-curl
HTTPCaller
    AUTH_METHOD = Basic
    AUTH_PASSWORD =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
    AUTH_USERNAME = admin
    CONNECTION_TIMEOUT_LENGTH = 60
    CUSTOM_HEADERS = Accept;text/html,application/xhtml+xml,application/xml;q=0.9,image/webp,*/*;q=0.8 Cookie;X-XSRF-TOKEN X-XSRF-TOKEN;8696ced3-704d-46a0-b8a0-60f5e66542fc Connection;keep-alive
    ERROR_ATTR = _error
    FOLLOW_REDIRECTS = No
    HTTP_METHOD = POST
    RESPONSE_HEADER_LIST_ATTR = List_header
    SAVE_FILE = Attribute
    STATUS_CODE_ATTR = _http_status_code
    TARGET_ATTR = _response_body
    TARGET_ATTR_ENCODING = auto-detect
    TARGET_URL = @Value(_root)/geonetwork/srv/api/records
    TRANSFER_TIMEOUT_LENGTH = 90
    UPLOAD_CONTENT_TYPE = Text (text/plain)
    UPLOAD_TYPE = Specify Upload Body
    USE_COOKIES = Yes
    VERIFY_SSL_CERTIFICATES = No
    <REJECTED> -> ListSearcher
ListSearcher
    ATTR_VALUE = XSRF-TOKEN
    INDEX_ATTR = _list_index
    LIST_ATTR = List_header{}.value
    MATCHTYPE = REGULAR_EXPRESSION_ENCODED
    PREFIX = _xsrf_token
    FOUND -> AttributeSplitter
AttributeSplitter
    ATTR_NAME = _xsrf_tokenvalue
    DELIMITER = ;
    DROP_EMPTY_PARTS = No
    LIST_NAME = _list
    TRIM_OPTION = Both
    -> AttributeCreator_5
AttributeCreator_5
    ATTR_TABLE = SET_TO _token = @Value(_list{0})
    -> AttributeTrimmer
AttributeTrimmer
    SRC_ATTRS = _token
    TRIM_CHARS = XSRF-TOKEN=
    TRIM_TO_NONE = Yes
    TRIM_TYPE = Left
    -> AttributeKeeper_2
AttributeKeeper_2
    KEEP_ATTRS = _root,_token,_group_id
    -> FeatureReader [INITIATOR]
FeatureHolder
    -> AttributeCreator_8
AttributeCreator_8
    ATTR_TABLE = SET_TO _file = $(PAYLOAD_TEMP_DIR)\@Value(path_rootname)_payload.txt
    -> HTTPCaller_2

Bookmark: Définir l'environnement
AttributeCreator_2
    ATTR_TABLE = SET_TO env = $(ENV)
    -> AttributeFilter
AttributeFilter
    ATTR_NAME = env
    ATTR_VALUES = <Empty>,<Missing>,<Null>,<Unfiltered>,PROD,STAGING,TEST
    PROD -> AttributeCreator_6
    STAGING -> AttributeCreator_3
    TEST -> AttributeCreator_7
AttributeCreator_6
    ATTR_TABLE = SET_TO _root = https://gcgeo.gc.ca
    -> HTTPCaller_3
AttributeCreator_3
    ATTR_TABLE = SET_TO _root = https://staging.gcgeo.gc.ca
    -> HTTPCaller_3
AttributeCreator_7
    ATTR_TABLE = SET_TO _root = https://test.gcgeo.gc.ca
    -> HTTPCaller_3

Bookmark: Obtenir le ID du groupe pour lequel on veut ajouter les données
HTTPCaller_3
    CONNECTION_TIMEOUT_LENGTH = 300
    CUSTOM_HEADERS = Accept;text/html,application/xhtml+xml,application/xml;q=0.9,image/webp,*/*;q=0.8
    ERROR_ATTR = _error
    FOLLOW_REDIRECTS = Yes
    HTTP_METHOD = GET
    SAVE_FILE = Attribute
    STATUS_CODE_ATTR = _http_status_code
    TARGET_ATTR = _response_body_groups
    TARGET_ATTR_ENCODING = auto-detect
    TARGET_URL = @Value(_root)/geonetwork/srv/api/groups?withReservedGroup=true
    TRANSFER_TIMEOUT_LENGTH = 300
    USE_COOKIES = Yes
    VERIFY_SSL_CERTIFICATES = No
    -> JSONFlattener
    <REJECTED> -> Terminator
JSONFlattener
    ERROR_LIST_ATTR = _json_error
    JSON_DOCUMENT = @Value(_response_body_groups)
    READ_FROM_FILE = NO
    RECURSIVE = Yes
    -> AttributeExposer_2
AttributeExposer_2
    ATTR_LIST = array{}.name,array{}.id
    -> ListExploder
ListExploder
    ATTR_ACCUM_MODE = Merge List Attributes
    ATTR_CONFLICT_RES = Use List Attribute Values
    INDEX_ATTR = _element_index
    LIST_ATTR = array{}
    ELEMENTS -> Tester_2
Tester_2
    BOOL_OP = OR
    COMPOSITE_TEST = 1
    TEST_CLAUSE = TEST @Value(name) = $(WORKSPACE)
    TEST_MODE = TEST
    PASSED -> AttributeCreator
AttributeCreator
    ATTR_TABLE = SET_TO _group_id = @Value(id)
    -> TerminatorMinMax
TerminatorMinMax
    Message = ERREUR : Problème avec le nom du groupe
    NombreEntitesMaximal = 1
    NombreEntitesMinimal = 1
    -> AttributeKeeper
AttributeKeeper
    KEEP_ATTRS = _root,_group_id
    -> HTTPCaller
Terminator
    MESSAGE = Translation Terminated

Bookmark: Lecture des fichierx XML
FeatureReader
    ATTR_ACCUM_MODE = Merge Initiator and Result
    ATTR_CONFLICT_RES = Use Result
    COMBINE_GEOM = Use Result
    DATASET = $(IN_XML_DIR)
    FORMAT = PATH
    OUTPUT_FEATURES_DISPLAY = Schema and Data Features
    PATH_GLOB_PATTERN = *
    PATH_NO_EMPTY_PROPERTIES = YES
    PATH_RECURSE_DIRECTORIES = NO
    PATH_RETRIEVE_FILE_PROPERTIES = NO
    PATH_TYPE = ANY
    <OTHER> -> AttributeExposer
AttributeExposer
    ATTR_LIST = path_windows,path_extension,path_filename,path_rootname
    -> FeatureReader_2 [INITIATOR]
FeatureReader_2
    ATTR_ACCUM_MODE = Merge Initiator and Result
    ATTR_CONFLICT_RES = Use Result
    COMBINE_GEOM = Use Result
    DATASET = @Value(path_windows)
    FORMAT = TEXTLINE
    OUTPUT_FEATURES_DISPLAY = Schema and Data Features
    TEXTLINE_CREATE_FEATURE_TABLES_FROM_DATA = Yes
    TEXTLINE_ENCODING = utf-8
    TEXTLINE_READ_WHOLE_FILE_AT_ONCE = YES
    <OTHER> -> AttributeExposer_3
AttributeExposer_3
    ATTR_LIST = text_line_data,path_extension
    -> Tester
Tester
    BOOL_OP = OR
    COMPOSITE_TEST = 1
    TEST_CLAUSE = TEST @Value(path_extension) = xml
    TEST_MODE = TEST
    PASSED -> RandomNumberGenerator

Bookmark: Écriture sur le disque du payload de manière temporaire
RandomNumberGenerator
    MAX = 999999999999999999999999999999
    MIN = 100000000000000000000000000000
    PLACES = 0
    RESULT_ATTR = _random_number
    -> AttributeCreator_4
AttributeCreator_4
    ATTR_TABLE:
      SET_TO payload = -----------------------------@Value(_random_number)
        Content-Disposition: form-data; name="language"

        eng
        -----------------------------@Value(_random_number)
        Content-Disposition: form-data; name="metadataType"

        METADATA
        -----------------------------@Value(_random_number)
        Content-Disposition: form-data; name="uuidProcessing"

        OVERWRITE
        -----------------------------@Value(_random_number)
        Content-Disposition: form-data; name="transformWith"


        -----------------------------@Value(_random_number)
        Content-Disposition: form-data; name="rejectIfInvalid"

        on
        -----------------------------@Value(_random_number)
        Content-Disposition: form-data; name="group"

        @Value(_group_id)
        -----------------------------@Value(_random_number)
        Content-Disposition: form-data; name="file"; filename="@Value(path_filename)"
        Content-Type: text/xml

        @Value(text_line_data)

        -----------------------------@Value(_random_number)--
    -> StringReplacer
StringReplacer
    CASE = NO
    FIND_TEXT = \n
    NO_MATCH = _FME_NO_OP_
    REGEXP = YES
    REPLACE_TEXT = $NIC$
    SRC_ATTRS = payload
    -> AttributeSplitter_2
AttributeSplitter_2
    ATTR_NAME = payload
    DELIMITER = $NIC$
    DROP_EMPTY_PARTS = No
    LIST_NAME = _list
    TRIM_OPTION = Both
    -> ListExploder_2
ListExploder_2
    ATTR_ACCUM_MODE = Merge List Attributes
    ATTR_CONFLICT_RES = Use List Attribute Values
    INDEX_ATTR = _element_index
    LIST_ATTR = _list{}
    ELEMENTS -> Sorter
Sorter
    SORT_PARM = path_filename ALPHA ASCENDING _element_index NUMERIC ASCENDING
    SORTED -> AttributeCreator_9
AttributeCreator_9
    ATTR_TABLE = SET_TO text_line_data = @Value(_list)
    -> FeatureWriter [text_line]
FeatureWriter
    DATASET = $(PAYLOAD_TEMP_DIR)\@Value(path_rootname)_payload.txt
    DATASET_ATTR = _dataset
    FEATURE_TYPE_LIST_ATTR = _feature_type
    FORMAT = TEXTLINE
    MORE_SUMMARY_ATTRS = _root _token path_rootname _random_number
    TEXTLINE_COORDINATE_SYSTEM_GRANULARITY = FEATURE
    TEXTLINE_DESTINATION_DATASETTYPE_VALIDATION = Yes
    TEXTLINE_ENCODING = UTF-8
    TEXTLINE_END_OF_LINE = Windows
    TEXTLINE_MIME_TYPE = text/plain
    TEXTLINE_OVERWRITE_FILE = YES
    TEXTLINE_WRITE_LAST_EOL = YES
    TEXTLINE_WRITE_UTF8_BOM = NO
    TOTAL_FEATURES_WRITTEN_ATTR = _total_features_written
    text_line -> DuplicateFilter
DuplicateFilter
    INPUT_ORDERED_CHOICE = No
    KEYATTR = path_rootname
    UNIQUE -> FeatureHolder

Bookmark: Préparation du paylod pour la requete post et exuction de la requete
HTTPCaller_2
    AUTH_METHOD = Basic
    AUTH_PASSWORD = $(AUTH_PASSWORD)
    AUTH_USERNAME = $(AUTH_USERNAME)
    CONNECTION_TIMEOUT_LENGTH = 60
    CUSTOM_HEADERS = X-XSRF-TOKEN;@Value(_token) Expect; Content-Type; multipart/form-data; boundary=---------------------------@Value(_random_number) Accept;application/json, text/javascript, */*; q=0.01
    ERROR_ATTR = _error
    FOLLOW_REDIRECTS = No
    HTTP_METHOD = POST
    MULTIPARTS = File FileUpload SOURCE_FILE;@Value(_file);MIME_TYPE;application/xml;FME_CONTROLLER_QUERY_FILE;transformers/dependencies/http/FileUpload.fme
    RESPONSE_HEADER_LIST_ATTR = list_header
    SAVE_FILE = Attribute
    STATUS_CODE_ATTR = _http_status_code
    TARGET_ATTR = _response_body
    TARGET_ATTR_ENCODING = auto-detect
    TARGET_URL = @Value(_root)/geonetwork/srv/api/records
    TRANSFER_TIMEOUT_LENGTH = 90
    UPLOAD_TYPE = Multipart / Form Data
    USE_COOKIES = Yes
    VERIFY_SSL_CERTIFICATES = No
    -> UPLOAD
    <REJECTED> -> HTTPCaller_2__Rejected_
UPLOAD: Inspector
HTTPCaller_2__Rejected_: Inspector
