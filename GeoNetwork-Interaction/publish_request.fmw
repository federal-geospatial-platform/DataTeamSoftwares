FME workspace publish_request.fmw

Parameters:
- ENV =
- AUTH_USERNAME =
- AUTH_PASSWORD =
- WORKSPACE_L2 =
- CONTENT_REVIEWER_USERNAME =   # ngariepy CONTENT_REVIEWER_USERNAME
- IN_DIR_XML =

Creator
    GEOMTYPE = Geometry Object
    NUM = 1
    CREATED -> AttributeCreator
HTTPCaller_7
    AUTH_METHOD = Basic
    AUTH_PASSWORD = $(AUTH_PASSWORD)
    AUTH_USERNAME = $(AUTH_USERNAME)
    CONNECTION_TIMEOUT_LENGTH = 60
    CUSTOM_HEADERS = Accept;application/json, text/plain, */*
    ERROR_ATTR = _error
    FOLLOW_REDIRECTS = Yes
    HTTP_METHOD = GET
    SAVE_FILE = Attribute
    STATUS_CODE_ATTR = _http_status_code
    TARGET_ATTR = _response_body_user
    TARGET_ATTR_ENCODING = auto-detect
    TARGET_URL = @Value(_root)/geonetwork/srv/api/users
    TRANSFER_TIMEOUT_LENGTH = 90
    USE_COOKIES = No
    VERIFY_SSL_CERTIFICATES = No
    -> JSONFlattener_2
JSONFlattener_2
    ERROR_LIST_ATTR = _json_error
    JSON_DOCUMENT = @Value(_response_body_user)
    READ_FROM_FILE = NO
    RECURSIVE = Yes
    -> AttributeExposer_3
AttributeExposer_3
    ATTR_LIST = array{}.id,array{}.username
    -> ListSearcher_3
ListSearcher_3
    ATTR_VALUE = $(CONTENT_REVIEWER_USERNAME)
    INDEX_ATTR = _list_index
    LIST_ATTR = array{}.username
    MATCHTYPE = FIRST_MATCHED_ENCODED
    PREFIX = _user_
    FOUND -> TerminatorMinMax_2
TerminatorMinMax_2
    Message = ERREUR : Problème avec le nom de l'usager
    NombreEntitesMaximal = 1
    NombreEntitesMinimal = 1
    -> AttributeKeeper_3
AttributeKeeper_3
    KEEP_ATTRS = _user_id,_group_id,_root
    -> HTTPCaller
HTTPCaller_3
    AUTH_METHOD = Basic
    AUTH_PASSWORD = $(AUTH_PASSWORD)
    AUTH_USERNAME = $(AUTH_USERNAME)
    CONNECTION_TIMEOUT_LENGTH = 60
    CUSTOM_HEADERS = X-XSRF-TOKEN;@Value(_token)
    ERROR_ATTR = _error
    FOLLOW_REDIRECTS = Yes
    HTTP_METHOD = POST
    MULTIPARTS = id StringUpload SOURCE_EXPRESSION;@Value(pub_id);MIME_TYPE;text/plain;FME_CONTROLLER_QUERY_FILE;transformers/dependencies/http/StringUpload.fme requestType StringUpload SOURCE_EXPRESSION;P;MIME_TYPE;text/plain;FME_CONTROLLER_QUERY_FILE;transformers/dependencies/http/StringUpload.fme _0 StringUpload SOURCE_EXPRESSION;true;MIME_TYPE;text/plain;FME_CONTROLLER_QUERY_FILE;transformers/dependencies/http/StringUpload.fme _@Value(_group_id) StringUpload SOURCE_EXPRESSION;on;MIME_TYPE;text/plain;FME_CONTROLLER_QUERY_FILE;transformers/dependencies/http/StringUpload.fme showLicense StringUpload SOURCE_EXPRESSION;y;MIME_TYPE;text/plain;FME_CONTROLLER_QUERY_FILE;transformers/dependencies/http/StringUpload.fme
    RESPONSE_HEADER_LIST_ATTR = list_response
    SAVE_FILE = Attribute
    STATUS_CODE_ATTR = _http_status_code
    TARGET_ATTR = _response_body
    TARGET_ATTR_ENCODING = auto-detect
    TARGET_URL = @Value(_root)/geonetwork/srv/canada/workflow/publish/eng
    TRANSFER_TIMEOUT_LENGTH = 90
    UPLOAD_TYPE = Multipart / Form Data
    USE_COOKIES = Yes
    VERIFY_SSL_CERTIFICATES = No
    -> HTTPCaller_4
    <REJECTED> -> HTTPCaller_3__Rejected_
HTTPCaller_4
    ADDITIONAL_URL_PARAMETERS = _content_type;html
    AUTH_METHOD = Basic
    AUTH_PASSWORD = $(AUTH_PASSWORD)
    AUTH_USERNAME = $(AUTH_USERNAME)
    CONNECTION_TIMEOUT_LENGTH = 60
    CUSTOM_HEADERS = X-XSRF-TOKEN;@Value(_token)
    ERROR_ATTR = _error
    FOLLOW_REDIRECTS = Yes
    HTTP_METHOD = POST
    MULTIPARTS = id StringUpload SOURCE_EXPRESSION;@Value(pub_id);MIME_TYPE;text/plain;FME_CONTROLLER_QUERY_FILE;transformers/dependencies/http/StringUpload.fme requestType StringUpload SOURCE_EXPRESSION;P;MIME_TYPE;text/plain;FME_CONTROLLER_QUERY_FILE;transformers/dependencies/http/StringUpload.fme _0 StringUpload SOURCE_EXPRESSION;true;MIME_TYPE;text/plain;FME_CONTROLLER_QUERY_FILE;transformers/dependencies/http/StringUpload.fme _@Value(_group_id) StringUpload SOURCE_EXPRESSION;on;MIME_TYPE;text/plain;FME_CONTROLLER_QUERY_FILE;transformers/dependencies/http/StringUpload.fme license_agreement_check StringUpload SOURCE_EXPRESSION;y;MIME_TYPE;text/plain;FME_CONTROLLER_QUERY_FILE;transformers/dependencies/http/StringUpload.fme mode StringUpload SOURCE_EXPRESSION;license;MIME_TYPE;text/plain;FME_CONTROLLER_QUERY_FILE;transformers/dependencies/http/StringUpload.fme
    RESPONSE_HEADER_LIST_ATTR = toto
    SAVE_FILE = Attribute
    STATUS_CODE_ATTR = _http_status_code
    TARGET_ATTR = _response_body
    TARGET_ATTR_ENCODING = auto-detect
    TARGET_URL = @Value(_root)/geonetwork/srv/canada/workflow/publish/eng
    TRANSFER_TIMEOUT_LENGTH = 90
    UPLOAD_TYPE = Multipart / Form Data
    USE_COOKIES = Yes
    VERIFY_SSL_CERTIFICATES = No
    <REJECTED> -> HTTPCaller_4__Rejected_
HTTPCaller_4__Rejected_: Inspector
HTTPCaller_3__Rejected_: Inspector

Bookmark: Ontenir l'environnement
AttributeCreator
    ATTR_TABLE = SET_TO env = $(ENV)
    -> AttributeFilter
AttributeFilter
    ATTR_NAME = env
    ATTR_VALUES = <Empty>,<Missing>,<Null>,<Unfiltered>,PROD,STAGING,TEST
    PROD -> AttributeCreator_3
    STAGING -> AttributeCreator_2
    TEST -> AttributeCreator_4
AttributeCreator_3
    ATTR_TABLE = SET_TO _root = https://gcgeo.gc.ca
    -> HTTPCaller_6
AttributeCreator_2
    ATTR_TABLE = SET_TO _root = https://staging.gcgeo.gc.ca
    -> HTTPCaller_6
AttributeCreator_4
    ATTR_TABLE = SET_TO _root = https://test.gcgeo.gc.ca
    -> HTTPCaller_6

Bookmark: Obtenir le ID du groupe pour lequel on veut ajouter les données
HTTPCaller_6
    CONNECTION_TIMEOUT_LENGTH = 300
    CUSTOM_HEADERS = Accept;text/html,application/xhtml+xml,application/xml;q=0.9,image/webp,*/*;q=0.8
    ERROR_ATTR = _error
    FOLLOW_REDIRECTS = Yes
    HTTP_METHOD = GET
    SAVE_FILE = Attribute
    STATUS_CODE_ATTR = _http_status_code
    TARGET_ATTR = _response_body_groups
    TARGET_ATTR_ENCODING = auto-detect
    TARGET_URL = @Value(_root)/geonetwork/srv/api/groups?withReservedGroup=true
    TRANSFER_TIMEOUT_LENGTH = 300
    USE_COOKIES = Yes
    VERIFY_SSL_CERTIFICATES = No
    -> JSONFlattener
    <REJECTED> -> Terminator
JSONFlattener
    ERROR_LIST_ATTR = _json_error
    JSON_DOCUMENT = @Value(_response_body_groups)
    READ_FROM_FILE = NO
    RECURSIVE = Yes
    -> AttributeExposer_2
AttributeExposer_2
    ATTR_LIST = array{}.name,array{}.id
    -> ListExploder
ListExploder
    ATTR_ACCUM_MODE = Merge List Attributes
    ATTR_CONFLICT_RES = Use List Attribute Values
    INDEX_ATTR = _element_index
    LIST_ATTR = array{}
    ELEMENTS -> Tester_2
Tester_2
    BOOL_OP = OR
    COMPOSITE_TEST = 1
    TEST_CLAUSE = TEST @Value(name) = $(WORKSPACE_L2)
    TEST_MODE = TEST
    PASSED -> AttributeCreator_9
AttributeCreator_9
    ATTR_TABLE = SET_TO _group_id = @Value(id)
    -> TerminatorMinMax
TerminatorMinMax
    Message = ERREUR : Problème avec le nom du groupe
    NombreEntitesMaximal = 1
    NombreEntitesMinimal = 1
    -> AttributeKeeper
AttributeKeeper
    KEEP_ATTRS = _root,_group_id
    -> HTTPCaller_7
Terminator
    MESSAGE = Translation Terminated

Bookmark: Fausse requete pour avoir un XSRF token
Note: Request Post bidon pour obtenir CSRF Token / La requête va planter mais on extrait le Token dans les cookies. La connection restera active et on utilisera la session après. / Voir doc GeoNetwork / https://geonetwork-opensource.org/manuals/trunk/en/customizing-application/misc.html#example-of-csrf-call-using-curl
HTTPCaller
    AUTH_METHOD = Basic
    AUTH_PASSWORD =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
    AUTH_USERNAME = admin
    CONNECTION_TIMEOUT_LENGTH = 60
    CUSTOM_HEADERS = Accept;text/html,application/xhtml+xml,application/xml;q=0.9,image/webp,*/*;q=0.8 Cookie;X-XSRF-TOKEN X-XSRF-TOKEN;8696ced3-704d-46a0-b8a0-60f5e66542fc Connection;keep-alive
    ERROR_ATTR = _error
    FOLLOW_REDIRECTS = No
    HTTP_METHOD = POST
    RESPONSE_HEADER_LIST_ATTR = List_header
    SAVE_FILE = Attribute
    STATUS_CODE_ATTR = _http_status_code
    TARGET_ATTR = _response_body
    TARGET_ATTR_ENCODING = auto-detect
    TARGET_URL = @Value(_root)/geonetwork/srv/api/records
    TRANSFER_TIMEOUT_LENGTH = 90
    UPLOAD_CONTENT_TYPE = Text (text/plain)
    UPLOAD_TYPE = Specify Upload Body
    USE_COOKIES = Yes
    VERIFY_SSL_CERTIFICATES = No
    <REJECTED> -> ListSearcher
ListSearcher
    ATTR_VALUE = XSRF-TOKEN
    INDEX_ATTR = _list_index
    LIST_ATTR = List_header{}.value
    MATCHTYPE = REGULAR_EXPRESSION_ENCODED
    PREFIX = _xsrf_token
    FOUND -> AttributeSplitter
AttributeSplitter
    ATTR_NAME = _xsrf_tokenvalue
    DELIMITER = ;
    DROP_EMPTY_PARTS = No
    LIST_NAME = _list
    TRIM_OPTION = Both
    -> AttributeCreator_5
AttributeCreator_5
    ATTR_TABLE = SET_TO _token = @Value(_list{0})
    -> AttributeTrimmer
AttributeTrimmer
    SRC_ATTRS = _token
    TRIM_CHARS = XSRF-TOKEN=
    TRIM_TO_NONE = Yes
    TRIM_TYPE = Left
    -> AttributeKeeper_2
AttributeKeeper_2
    KEEP_ATTRS = _user_id,_token,_group_id,_root
    -> FeatureReader [INITIATOR]

Bookmark: Lecture des fichiers à publier
FeatureReader
    ATTR_ACCUM_MODE = Merge Initiator and Result
    ATTR_CONFLICT_RES = Use Result
    COMBINE_GEOM = Use Result
    DATASET = $(IN_DIR_XML)
    FORMAT = PATH
    OUTPUT_FEATURES_DISPLAY = Schema and Data Features
    PATH_GLOB_PATTERN = *
    PATH_NO_EMPTY_PROPERTIES = YES
    PATH_RECURSE_DIRECTORIES = NO
    PATH_RETRIEVE_FILE_PROPERTIES = NO
    PATH_TYPE = ANY
    <OTHER> -> AttributeExposer
AttributeExposer
    ATTR_LIST = path_windows
    -> XMLFlattener
XMLFlattener
    EMBEDDED_EXPRESSIONS = MD_Metadata/fileIdentifier/CharacterString
    FEATURE_TYPES_FORMAT_NAME = XML
    FILE_XML = @Value(path_windows)
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = CharacterString
    XML_SOURCE_TYPE = XML file
    -> AttributeCreator_6
AttributeCreator_6
    ATTR_TABLE = SET_TO uuid = @Value(CharacterString)
    -> HTTPCaller_2

Bookmark: Requete #1- Get Publish + extraction publication ID
HTTPCaller_2
    ADDITIONAL_URL_PARAMETERS = uuid;@Value(uuid) _content_type;html
    AUTH_METHOD = Basic
    AUTH_PASSWORD = $(AUTH_PASSWORD)
    AUTH_USERNAME = $(AUTH_USERNAME)
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(_root)/geonetwork/srv/canada/workflow/publish/eng
    TRANSFER_TIMEOUT_LENGTH = 90
    USE_COOKIES = No
    VERIFY_SSL_CERTIFICATES = Yes
    -> AttributeSplitter_2
    <REJECTED> -> HTTPCaller_2__Rejected_
HTTPCaller_2__Rejected_: Inspector

Bookmark: Extraction du ID en fonction du retour HTML
AttributeSplitter_2
    ATTR_NAME = _response_body
    DELIMITER = <input
    DROP_EMPTY_PARTS = No
    LIST_NAME = _list
    TRIM_OPTION = Both
    -> ListSearcher_2
ListSearcher_2
    ATTR_VALUE = name="id" id="id"
    INDEX_ATTR = _list_index
    LIST_ATTR = _list{}
    MATCHTYPE = REGULAR_EXPRESSION_ENCODED
    PREFIX = pub_id
    FOUND -> AttributeRemover
AttributeRemover
    LIST_ATTRS = _list{}
    -> AttributeSplitter_3
AttributeSplitter_3
    ATTR_NAME = pub_id_list
    DELIMITER = value="
    DROP_EMPTY_PARTS = No
    LIST_NAME = _list
    TRIM_OPTION = Both
    -> AttributeCreator_7
AttributeCreator_7
    ATTR_TABLE = SET_TO pub_id = @Value(_list{1})
    -> AttributeTrimmer_2
AttributeTrimmer_2
    SRC_ATTRS = pub_id
    TRIM_CHARS = ">
    TRIM_TO_NONE = Yes
    TRIM_TYPE = Both
    -> HTTPCaller_5

Bookmark: Requete #4- Submit
HTTPCaller_5
    AUTH_METHOD = Basic
    AUTH_PASSWORD = $(AUTH_PASSWORD)
    AUTH_USERNAME = $(AUTH_USERNAME)
    CONNECTION_TIMEOUT_LENGTH = 60
    CUSTOM_HEADERS = X-XSRF-TOKEN;@Value(_token) Expect;
    ERROR_ATTR = _error
    FOLLOW_REDIRECTS = No
    HTTP_METHOD = POST
    MULTIPARTS = _content_type StringUpload SOURCE_EXPRESSION;html;MIME_TYPE;text/plain;FME_CONTROLLER_QUERY_FILE;transformers/dependencies/http/StringUpload.fme id StringUpload SOURCE_EXPRESSION;@Value(pub_id);MIME_TYPE;text/plain;FME_CONTROLLER_QUERY_FILE;transformers/dependencies/http/StringUpload.fme requestType StringUpload SOURCE_EXPRESSION;P;MIME_TYPE;text/plain;FME_CONTROLLER_QUERY_FILE;transformers/dependencies/http/StringUpload.fme validateBothLanguages StringUpload SOURCE_EXPRESSION;true;MIME_TYPE;text/plain;FME_CONTROLLER_QUERY_FILE;transformers/dependencies/http/StringUpload.fme _0 StringUpload SOURCE_EXPRESSION;on;MIME_TYPE;text/plain;FME_CONTROLLER_QUERY_FILE;transformers/dependencies/http/StringUpload.fme _@Value(_group_id) StringUpload SOURCE_EXPRESSION;on;MIME_TYPE;text/plain;FME_CONTROLLER_QUERY_FILE;transformers/dependencies/http/StringUpload.fme contentReviewer StringUpload SOURCE_EXPRESSION;@Value(_user_id);MIME_TYPE;text/plain;FME_CONTROLLER_QUERY_FILE;transformers/dependencies/http/StringUpload.fme additionalMailCC StringUpload SOURCE_EXPRESSION;&attachFile;MIME_TYPE;text/plain;FME_CONTROLLER_QUERY_FILE;transformers/dependencies/http/StringUpload.fme comments_request StringUpload SOURCE_EXPRESSION;approved;MIME_TYPE;text/plain;FME_CONTROLLER_QUERY_FILE;transformers/dependencies/http/StringUpload.fme
    RESPONSE_HEADER_LIST_ATTR = toto
    SAVE_FILE = Attribute
    STATUS_CODE_ATTR = _http_status_code
    TARGET_ATTR = _response_body
    TARGET_ATTR_ENCODING = auto-detect
    TARGET_URL = @Value(_root)/geonetwork/srv/canada/workflow/submit/eng
    TRANSFER_TIMEOUT_LENGTH = 90
    UPLOAD_TYPE = Multipart / Form Data
    USE_COOKIES = Yes
    VERIFY_SSL_CERTIFICATES = No
    -> SUBMIT
    <REJECTED> -> HTTPCaller_5__Rejected_
SUBMIT: Inspector
HTTPCaller_5__Rejected_: Inspector
