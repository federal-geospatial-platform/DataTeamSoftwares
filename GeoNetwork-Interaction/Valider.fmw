FME workspace Valider.fmw

Parameters:
- ENV = TEST
- IN_DIR_XML = $(FME_MF_DIR)test
- DATETIME = 20201021100000
- OUT_XML_RELOAD_DIR = $(FME_MF_DIR)reload_20201021110122

Creator_2
    GEOMTYPE = Geometry Object
    NUM = 1
    CREATED -> DateTimeStamper
DateTimeStamper
    DATETIME_ATTR = _timestamp
    INCLUDE_OFFSET = NO
    STAMP_TYPE = datetime
    TIMEZONE = local
    -> DateTimeConverter_3
DateTimeConverter_3
    DATETIME_ATTR = _timestamp
    OUT_FORMAT = %Y%m%d%H%M%S
    PASSTHROUGH = NO
    REPAIR_INPUT = YES
    -> AttributeCreator
AttributeCreator
    ATTR_TABLE = SET_TO nom_dir = @Evaluate(@ceil(@Value(_timestamp)))
    -> AttributeCreator_2
HTTPCaller
    CONNECTION_TIMEOUT_LENGTH = 60
    ERROR_ATTR = _error
    FOLLOW_REDIRECTS = Yes
    HTTP_METHOD = POST
    SAVE_FILE = Attribute
    STATUS_CODE_ATTR = _http_status_code
    TARGET_ATTR = _response_body
    TARGET_ATTR_ENCODING = auto-detect
    TARGET_URL = @Value(_root_interne)/geonetwork/srv/csw
    TRANSFER_TIMEOUT_LENGTH = 90
    UPLOAD_BODY:
      <csw:GetRecords xmlns:csw="http://www.opengis.net/cat/csw/2.0.2"
          xmlns:gmd="http://www.isotc211.org/2005/gmd" service="CSW" version="2.0.2"
          resultType="results_with_summary" startPosition='1' maxRecords='10'>
          <csw:Query typeNames="gmd:MD_Metadata">
          <csw:Constraint version="1.1.0">
            <Filter xmlns="http://www.opengis.net/ogc" xmlns:gml="http://www.opengis.net/gml">
              <PropertyIsEqualTo>
                <PropertyName>dc:identifier</PropertyName>
                <Literal>@Value(uuid)</Literal>
              </PropertyIsEqualTo>
            </Filter>
          </csw:Constraint>
          </csw:Query>
      </csw:GetRecords>
    UPLOAD_CONTENT_TYPE = XML (application/xml)
    UPLOAD_TYPE = Specify Upload Body
    USE_COOKIES = No
    VERIFY_SSL_CERTIFICATES = Yes
    -> XMLFlattener_2
XMLFlattener_2
    ATTRIBUTE_XML = _response_body
    EMBEDDED_EXPRESSIONS = GetRecordsResponse/SearchResults/Record/info/changeDate
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = changeDate
    XML_SOURCE_TYPE = Attribute with XML document
    -> DateTimeConverter
DateTimeConverter
    DATETIME_ATTR = changeDate
    OUT_FORMAT = %Y%m%d%H%M%S
    PASSTHROUGH = NO
    REPAIR_INPUT = YES
    -> Tester
Tester
    BOOL_OP = OR
    COMPOSITE_TEST = 1
    TEST_CLAUSE = TEST @Value(changeDate) >= $(DATETIME)
    TEST_MODE = TEST
    PASSED -> Tester_Passed
    FAILED -> Tester_Failed
Tester_Passed: Inspector
Tester_Failed: Inspector
HTTPCaller_2
    CONNECTION_TIMEOUT_LENGTH = 60
    ERROR_ATTR = _error
    FOLLOW_REDIRECTS = Yes
    HTTP_METHOD = POST
    SAVE_FILE = Attribute
    STATUS_CODE_ATTR = _http_status_code
    TARGET_ATTR = _response_body
    TARGET_ATTR_ENCODING = auto-detect
    TARGET_URL = @Value(_root_externe)/geonetwork/srv/csw
    TRANSFER_TIMEOUT_LENGTH = 90
    UPLOAD_BODY:
      <csw:GetRecords xmlns:csw="http://www.opengis.net/cat/csw/2.0.2"
          xmlns:gmd="http://www.isotc211.org/2005/gmd" service="CSW" version="2.0.2"
          resultType="results_with_summary" startPosition='1' maxRecords='10'>
          <csw:Query typeNames="gmd:MD_Metadata">
          <csw:Constraint version="1.1.0">
            <Filter xmlns="http://www.opengis.net/ogc" xmlns:gml="http://www.opengis.net/gml">
              <PropertyIsEqualTo>
                <PropertyName>dc:identifier</PropertyName>
                <Literal>@Value(uuid)</Literal>
              </PropertyIsEqualTo>
            </Filter>
          </csw:Constraint>
          </csw:Query>
      </csw:GetRecords>
    UPLOAD_CONTENT_TYPE = XML (application/xml)
    UPLOAD_TYPE = Specify Upload Body
    USE_COOKIES = No
    VERIFY_SSL_CERTIFICATES = Yes
    -> XMLFlattener_3
XMLFlattener_3
    ATTRIBUTE_XML = _response_body
    EMBEDDED_EXPRESSIONS = GetRecordsResponse/SearchResults/Record/info/changeDate
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = changeDate
    XML_SOURCE_TYPE = Attribute with XML document
    -> DateTimeConverter_2
    <REJECTED> -> SystemCaller
DateTimeConverter_2
    DATETIME_ATTR = changeDate
    OUT_FORMAT = %Y%m%d%H%M%S
    PASSTHROUGH = NO
    REPAIR_INPUT = YES
    -> Tester_2
Tester_2
    BOOL_OP = OR
    COMPOSITE_TEST = 1
    TEST_CLAUSE = TEST @Value(changeDate) >= $(DATETIME)
    TEST_MODE = TEST
    PASSED -> Tester_2_Passed
    FAILED -> Tester_2_Failed
    FAILED -> SystemCaller
Tester_2_Passed: Inspector
Tester_2_Failed: Inspector
SystemCaller
    CMD = IF NOT EXIST $(OUT_XML_RELOAD_DIR)\reload_@Value(nom_dir) mkdir $(OUT_XML_RELOAD_DIR)\reload_@Value(nom_dir)
    -> SystemCaller_2
SystemCaller_2
    CMD = COPY @Value(path_windows) $(OUT_XML_RELOAD_DIR)\reload_@Value(nom_dir)

Bookmark: Sélection de l'environnement
AttributeCreator_2
    ATTR_TABLE = SET_TO env = $(ENV)
    -> AttributeFilter
AttributeFilter
    ATTR_NAME = env
    ATTR_VALUES = <Empty>,<Missing>,<Null>,<Unfiltered>,PROD,STAGING,TEST
    PROD -> AttributeCreator_5
    STAGING -> AttributeCreator_4
    TEST -> AttributeCreator_6
AttributeCreator_5
    ATTR_TABLE:
      SET_TO _root_interne = https://gcgeo.gc.ca
      SET_TO _root_externe = https://maps.canada.ca
    -> FeatureReader [INITIATOR]
AttributeCreator_4
    ATTR_TABLE:
      SET_TO _root_interne = https://staging.gcgeo.gc.ca
      SET_TO _root_externe = https://maps-staging.canada.ca
    -> FeatureReader [INITIATOR]
AttributeCreator_6
    ATTR_TABLE:
      SET_TO _root_interne = https://test.gcgeo.gc.ca
      SET_TO _root_externe = https://maps-test.canada.ca
    -> FeatureReader [INITIATOR]

Bookmark: Lecture des fichiers à vérifier
FeatureReader
    ATTR_ACCUM_MODE = Merge Initiator and Result
    ATTR_CONFLICT_RES = Use Result
    COMBINE_GEOM = Use Result
    DATASET = $(IN_DIR_XML)
    FORMAT = PATH
    OUTPUT_FEATURES_DISPLAY = Schema and Data Features
    PATH_GLOB_PATTERN = *
    PATH_NO_EMPTY_PROPERTIES = YES
    PATH_RECURSE_DIRECTORIES = NO
    PATH_RETRIEVE_FILE_PROPERTIES = NO
    PATH_TYPE = ANY
    <OTHER> -> AttributeExposer
AttributeExposer
    ATTR_LIST = path_windows
    -> XMLFlattener
XMLFlattener
    EMBEDDED_EXPRESSIONS = MD_Metadata/fileIdentifier/CharacterString
    FEATURE_TYPES_FORMAT_NAME = XML
    FILE_XML = @Value(path_windows)
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = CharacterString
    XML_SOURCE_TYPE = XML file
    -> AttributeCreator_3
AttributeCreator_3
    ATTR_TABLE = SET_TO uuid = @Value(CharacterString)
    -> HTTPCaller
    -> HTTPCaller_2
