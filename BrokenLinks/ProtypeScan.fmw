FME workspace ProtypeScan.fmw

Parameters:
- IN_OUT_SQLLITE_FILE = $(FME_MF_DIR)ValidationBrokenLinks.db
- LOG_FILE =

Readers:
- SQLITE3_1: SQLITE3 from $(IN_OUT_SQLLITE_FILE)

Writers:
- SQLITE3_2: SQLITE3 to $(IN_OUT_SQLLITE_FILE)

ListExploder
    ATTR_ACCUM_MODE = Prefix List Attributes
    INCOMING_PREFIX = MD_Metadata.distributionInfo.MD_Distribution.transferOptions.
    INDEX_ATTR = _element_index
    LIST_ATTR = MD_Metadata.distributionInfo.MD_Distribution.transferOptions{}
    ELEMENTS -> ListExploder_2
    <REJECTED> -> ListExploder_2
ListExploder_2
    ATTR_ACCUM_MODE = Prefix List Attributes
    INCOMING_PREFIX = MD_Metadata.distributionInfo.MD_Distribution.transferOptions.MD_DigitalTransferOptions.onLine.
    INDEX_ATTR = _element_index
    LIST_ATTR = MD_Metadata.distributionInfo.MD_Distribution.transferOptions.MD_DigitalTransferOptions.onLine{}
    ELEMENTS -> AttributeSplitter
    <REJECTED> -> AttributeSplitter
AttributeSplitter
    ATTR_NAME = MD_Metadata.distributionInfo.MD_Distribution.transferOptions.MD_DigitalTransferOptions.onLine.CI_OnlineResource.description.CharacterString
    DELIMITER = ;
    DROP_EMPTY_PARTS = No
    LIST_NAME = _listdescription
    TRIM_OPTION = Both
    -> AttributeCreator
AttributeCreator
    ATTR_TABLE:
      SET_TO _format = @Value(_listdescription{1})
      SET_TO _uuid = @Value(MD_Metadata.fileIdentifier.CharacterString)
      SET_TO _url = @Value(MD_Metadata.distributionInfo.MD_Distribution.transferOptions.MD_DigitalTransferOptions.onLine.CI_OnlineResource.linkage.URL)
      SET_TO DATASET_TITLE = @Value(MD_Metadata.identificationInfo.MD_DataIdentification.citation.CI_Citation.title.CharacterString)
    -> DuplicateFilter
DuplicateFilter
    INPUT_ORDERED_CHOICE = No
    KEYATTR = _uuid _url
    UNIQUE -> AttributeKeeper
AttributeKeeper
    KEEP_ATTRS = DATASET_TITLE,_url,_format,_uuid
    -> AttributeFilter
AttributeFilter
    ATTR_NAME = _format
    ATTR_VALUES = <Empty>,<Missing>,<Null>,<Unfiltered>,WMS
    WMS -> WMS_LINK_VALIDATOR [HTTPCaller_Input]
BROKEN_LINKS (reader SQLITE3_1)
    attributes: METADATA_UUID text,Unique, DATASET_TITLE text, URL text,Unique, RESOURCE_FORMAT text, BROKEN_LINK_PROBLEM text, BROKEN_LINK_STATUS_DATE text,Unique, BROKEN_LINK_STATUS text,Unique, EMAIL_STATUS text
    -> DateTimeConverter_2
FeatureMerger_2
    ATTR_ACCUM_MODE = Merge Supplier
    ATTR_CONFLICT_RES = Use Requestor
    IGNORE_NULLS = No
    JOIN_KEYS = @Value(URL) @Value(URL) AUTO @Value(METADATA_UUID) @Value(METADATA_UUID) AUTO
    MERGE_TYPE = Attributes Only
    PROCESS_DUPS = NO
    REJECT_NULL_MISSING_KEYS = No
    SUPPLIERS_FIRST = No
    MERGED -> AttributeFilter_2
    UNMERGED_REQUESTOR -> BROKEN_LINKS (writer SQLITE3_2)
    UNUSED_SUPPLIER -> Tester
    <REJECTED> -> Terminator_3
AttributeFilter_2
    ATTR_NAME = latest_observationBROKEN_LINK_STATUS
    ATTR_VALUES = <Empty>,<Missing>,<Null>,<Unfiltered>,FIXED,OBSERVED,CONFIRMED
    <EMPTY> -> Terminator
    <MISSING> -> Terminator
    <NULL> -> Terminator
    <UNFILTERED> -> Terminator
    FIXED -> BROKEN_LINKS (writer SQLITE3_2)
    OBSERVED -> AttributeCreator_6
    CONFIRMED -> StatisticsCalculator
Terminator
    MESSAGE = Translation Terminated
AttributeCreator_6
    ATTR_TABLE:
      SET_TO BROKEN_LINK_STATUS = CONFIRMED
      SET_TO EMAIL_STATUS = TO_DO
    -> BROKEN_LINKS (writer SQLITE3_2)
StatisticsCalculator
    COMPUTE_HISTOGRAM = NO
    COUNT_ATTR = _count
    PREPEND_ATTR_NAME_CHOICE = For multiple results only
    STATS_ATTRS = URL
    SUMMARY -> Logger
Logger
    LOG_FEATURE = LOG_ONLY
    MAXCOORDS = 20
    MAXFEATS = 1
    MESSAGE = @Value(_count) features already confirmed were detected
    SEVERITY = INFO
Note: Écriture dans la base de données, un pré SQL est fait pour activer les clé étrangères dans la base de données.
BROKEN_LINKS (writer SQLITE3_2)
    attributes: METADATA_UUID text,Unique, DATASET_TITLE text, URL text,Unique, RESOURCE_FORMAT text, BROKEN_LINK_PROBLEM text, BROKEN_LINK_STATUS text,Unique, BROKEN_LINK_STATUS_DATE text,Unique, EMAIL_STATUS text
Terminator_3
    MESSAGE = Translation Terminated

Bookmark: Lecture du catalogue (Catalogue Reader)
Creator
    GEOMTYPE = Geometry Object
    NUM = 1
    CREATED -> FeatureReader [INITIATOR]
FeatureReader
    ATTR_ACCUM_MODE = Only Use Result
    COMBINE_GEOM = Use Result
    DATASET = $(FME_MF_DIR_ENCODED)Source.ffs
    FFS_USE_SEARCH_ENVELOPE = NO
    FORMAT = FFS
    INTERACT = <No Spatial Filter>
    OUTPUT_FEATURES_DISPLAY = Schema and Data Features
    <OTHER> -> AttributeExposer
    <REJECTED> -> Terminator_4
AttributeExposer
    ATTR_LIST = MD_Metadata.distributionInfo.MD_Distribution.transferOptions{}.MD_DigitalTransferOptions.onLine{}.CI_OnlineResource.linkage.URL,MD_Metadata.distributionInfo.MD_Distribution.transferOptions{}.MD_DigitalTransferOptions.onLine{}.CI_OnlineResource.description.CharacterString,MD_Metadata.fileIdentifier.CharacterString,MD_Metadata.identificationInfo.MD_DataIdentification.citation.CI_Citation.title.CharacterString
    -> ListExploder
Terminator_4
    MESSAGE = Translation Terminated

Bookmark: Validation du WMS
WMS_LINK_VALIDATOR
    URL = @Value(_url)
    BROKEN_URL_LINK -> AttributeCreator_3
    INVALID_WMS_URL -> AttributeCreator_2
    WMS_UNREFERENCED_LAYER -> AttributeCreator_4
Note: Définition du statut
AttributeCreator_5
    ATTR_TABLE:
      SET_TO BROKEN_LINK_STATUS = OBSERVED
      SET_TO METADATA_UUID = @Value(_uuid)
      SET_TO RESOURCE_FORMAT = WMS
      SET_TO URL = @Value(_url)
      SET_TO EMAIL_STATUS = NOT_APPLICABLE
    -> DateTimeStamper
Note: Date de l'observation
DateTimeStamper
    DATETIME_ATTR = BROKEN_LINK_STATUS_DATE
    INCLUDE_OFFSET = NO
    STAMP_TYPE = datetime
    TIMEZONE = local
    -> DateTimeConverter
DateTimeConverter
    DATETIME_ATTR = BROKEN_LINK_STATUS_DATE
    OUT_FORMAT = %Y-%m-%dT%H:%M:%S
    PASSTHROUGH = NO
    REPAIR_INPUT = YES
    -> FeatureMerger_2 [REQUESTOR]

Bookmark: Définition du problème
AttributeCreator_3
    ATTR_TABLE = SET_TO BROKEN_LINK_PROBLEM = WMS_URL_NOT_RESPONDING
    -> AttributeCreator_5
AttributeCreator_2
    ATTR_TABLE = SET_TO BROKEN_LINK_PROBLEM = WMS_URL_STRUCTURE
    -> AttributeCreator_5
AttributeCreator_4
    ATTR_TABLE = SET_TO BROKEN_LINK_PROBLEM = WMS_UNREFERENCED_LAYER
    -> AttributeCreator_5

Bookmark: Lecture de la BD et identification de la dernière observation du lien brisé par URL/UUID
Note: Ajustement du format de date
DateTimeConverter_2
    DATETIME_ATTR = BROKEN_LINK_STATUS_DATE
    IN_FORMAT = %Y-%m-%dT%H:%M:%S$
    OUT_FORMAT = FME
    PASSTHROUGH = NO
    REPAIR_INPUT = YES
    -> ListBuilder
    <REJECTED> -> Terminator_2
Note: Regrouper les entités par UUID/URL
ListBuilder
    GROUP_BY = URL METADATA_UUID
    LIST_NAME = _list
    -> ListSorter
Note: Trier en ordre décroissant de date
ListSorter
    ORDER = Descending
    SRC_LIST = _list{}.BROKEN_LINK_STATUS_DATE
    TYPE = Numeric
    -> ListIndexer
ListIndexer
    INDEX = 0
    LIST_ATTR = _list{}
    PREFIX = latest_observation
    -> AttributeKeeper_2
AttributeKeeper_2
    KEEP_ATTRS = latest_observationRESOURCE_FORMAT,METADATA_UUID,URL,latest_observationDATASET_TITLE,latest_observationBROKEN_LINK_PROBLEM,latest_observationBROKEN_LINK_STATUS,latest_observationEMAIL_STATUS
    -> FeatureMerger_2 [SUPPLIER]
Terminator_2
    MESSAGE = Translation Terminated

Bookmark: Broken link fixed
Tester
    BOOL_OP = OR
    COMPOSITE_TEST = 1
    TEST_CLAUSE = TEST @Value(latest_observationBROKEN_LINK_STATUS) != FIXED
    TEST_MODE = TEST
    PASSED -> BulkAttributeRenamer
BulkAttributeRenamer
    ATTRCHOICE = Selected Attributes
    ATTRLIST = latest_observationRESOURCE_FORMAT latest_observationDATASET_TITLE latest_observationBROKEN_LINK_PROBLEM
    CASE_DISP = YES
    MODE_CHOICE = RENAME
    PATTERN_ACTION_DISP = REMOVEPREFIX
    REPLACE_STR = latest_observation
    -> AttributeCreator_11
AttributeCreator_11
    ATTR_TABLE:
      SET_TO BROKEN_LINK_STATUS = FIXED
      SET_TO EMAIL_STATUS = NOT_APPLICABLE
    -> DateTimeStamper_2
DateTimeStamper_2
    DATETIME_ATTR = BROKEN_LINK_STATUS_DATE
    INCLUDE_OFFSET = NO
    STAMP_TYPE = datetime
    TIMEZONE = local
    -> DateTimeConverter_3
DateTimeConverter_3
    DATETIME_ATTR = BROKEN_LINK_STATUS_DATE
    OUT_FORMAT = %Y-%m-%dT%H:%M:%S
    PASSTHROUGH = NO
    REPAIR_INPUT = YES
    -> BROKEN_LINKS (writer SQLITE3_2)

FME custom transformer WMS_LINK_VALIDATOR

Parameters:
- URL =

HTTPCaller_Input (input)
    -> AttributeCreator
AttributeCreator
    ATTR_TABLE = SET_TO _url2validate = $(URL)
    -> Tester
Tester
    BOOL_OP = COMPOSITE
    COMPOSITE_TEST = 1 AND 2
    TEST_CLAUSE:
      CASE_INSENSITIVE_TEST @Value(_url2validate) CONTAINS request=GetCapabilities
      CASE_INSENSITIVE_TEST @Value(_url2validate) CONTAINS service=WMS
    TEST_MODE = CASE_INSENSITIVE_TEST
    PASSED -> HTTPCaller
    FAILED -> INVALID_WMS_URL (output)
HTTPCaller
    CONNECTION_TIMEOUT_LENGTH = 10
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(_url2validate)
    TRANSFER_TIMEOUT_LENGTH = 15
    USE_COOKIES = No
    VERIFY_SSL_CERTIFICATES = No
    -> Tester_2
    <REJECTED> -> BROKEN_URL_LINK (output)
Tester_2
    BOOL_OP = OR
    COMPOSITE_TEST = 1
    TEST_CLAUSE = TEST @Value(_http_status_code) = 200
    TEST_MODE = TEST
    PASSED -> AttributeSplitter
    FAILED -> BROKEN_URL_LINK (output)
WMS_UNREFERENCED_LAYER (output)
BROKEN_URL_LINK (output)
INVALID_WMS_URL (output)

Bookmark: Evaluation de la présence des bonnes couches dans la requête GetCapabilities
Note: Division de la requête
AttributeSplitter
    ATTR_NAME = _url2validate
    DELIMITER = &
    DROP_EMPTY_PARTS = No
    LIST_NAME = _listwms
    TRIM_OPTION = Both
    -> ListSearcher
Note: Recherche du layer
ListSearcher
    ATTR_VALUE = layers
    INDEX_ATTR = _list_index
    LIST_ATTR = _listwms{}
    MATCHTYPE = REGULAR_EXPRESSION_ENCODED
    FOUND -> ListIndexer
ListIndexer
    INDEX = @Value(_list_index)
    LIST_ATTR = _listwms{}
    PREFIX = layer_values
    -> AttributeSplitter_2
AttributeSplitter_2
    ATTR_NAME = layer_values_listwms
    DELIMITER = =
    DROP_EMPTY_PARTS = No
    LIST_NAME = _list
    TRIM_OPTION = Both
    -> AttributeCreator_2
AttributeCreator_2
    ATTR_TABLE = SET_TO layer_name = @Value(_list{1})
    -> AttributeRemover
AttributeRemover
    LIST_ATTRS = _list{} _listwms{}
    REMOVE_ATTRS = layer_values_listwms,_list_index
    -> UUIDGenerator
UUIDGenerator
    UUID_ATTR = _uuid_temp
    -> XMLFormatter
    -> FeatureMerger [REQUESTOR]
XMLFormatter
    COLLAPSE_EMPTY_ELEMENT = Yes
    FORMATTING_CHOICE = Linearize XML
    LIST_NAME = _xml_error
    NAMESPACE_CLEANUP = Yes
    OUTPUT_ENCODING = utf-8
    REMOVE_ALL_COMMENT = Yes
    REMOVE_EMPTY_ELEMENT = Yes
    SCHEMALOC_CLEANUP = Yes
    WHITESPACE_HANDLING = Remove excess whitespace
    XML_ATTR_TEXT = _response_body
    XML_INPUT_TYPE = Attribute Specifying XML Text
    XML_OUTPUT_ATTR = _xml_output
    XML_OUTPUT_TYPE = Attribute
    PASSED -> XMLFragmenter
XMLFragmenter
    ATTRIBUTE_XML = _xml_output
    EMBEDDED_EXPRESSIONS = Layer
    FEATURE_TYPES_FORMAT_NAME = XML
    MERGE_ATTRS = Yes
    REJECT_FEATURES_WITH_NO_FRAGMENTS = YES
    XML_SOURCE_TYPE = Attribute with XML document
    FRAGMENTS -> XMLFlattener
    <REJECTED> -> Cloner
XMLFlattener
    ATTRIBUTE_XML = xml_fragment
    EMBEDDED_EXPRESSIONS = Layer
    FEATURE_TYPES_FORMAT_NAME = XML
    FLATTEN_OPTIONS = <structure separator="." map-empty-elements="yes" matched-prefix="attributes" matched-attributes="yes" cardinality="+{?}" structure-prefix="" child-position-attribute="" except-expression="Layer" ui-mode="basic" matched-ancestor-attributes=""/>
    NEW_ATTRIBUTES = Name
    XML_SOURCE_TYPE = Attribute with XML document
    -> ListBuilder_2
ListBuilder_2
    GROUP_BY = _uuid_temp
    LIST_ATTRS_TO_INCLUDE = Name
    LIST_NAME = _list
    -> ListDuplicateRemover
ListDuplicateRemover
    SRC_LIST = _list{}.Name
    -> FeatureMerger [SUPPLIER]
FeatureMerger
    ATTR_ACCUM_MODE = Merge Supplier
    ATTR_CONFLICT_RES = Use Requestor
    IGNORE_NULLS = No
    JOIN_KEYS = @Value(_uuid_temp) @Value(_uuid_temp) AUTO
    MERGE_TYPE = Attributes Only
    PROCESS_DUPS = NO
    REJECT_NULL_MISSING_KEYS = No
    SUPPLIERS_FIRST = No
    MERGED -> AttributeSplitter_3
    UNMERGED_REQUESTOR -> WMS_UNREFERENCED_LAYER (output)
Cloner
    COPIES = 1
    COPYATT = _copynum

Bookmark: Recherche des noms de couche dans le résultat du GetCapabilities
AttributeSplitter_3
    ATTR_NAME = layer_name
    DELIMITER = ,
    DROP_EMPTY_PARTS = Yes
    LIST_NAME = _list_layername
    TRIM_OPTION = Both
    -> ListExploder
ListExploder
    ATTR_ACCUM_MODE = Merge List Attributes
    ATTR_CONFLICT_RES = Use List Attribute Values
    INDEX_ATTR = _element_index
    LIST_ATTR = _list_layername{}
    ELEMENTS -> ListSearcher_2
    <REJECTED> -> Terminator
ListSearcher_2
    ATTR_VALUE = @Value(_list_layername)
    INDEX_ATTR = _list_index
    LIST_ATTR = _list{}.Name
    MATCHTYPE = FIRST_MATCHED_ENCODED
    NOT_FOUND -> AttributeRemover_2
AttributeRemover_2
    LIST_ATTRS = _list{}
    -> WMS_UNREFERENCED_LAYER (output)
Terminator
    MESSAGE = Translation Terminated
