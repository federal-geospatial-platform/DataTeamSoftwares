FME workspace ChargerMetaPyCSW.fmw

Parameters:
- IN_XML_FILE = C:\Users\ngariepy\Downloads\XML_LOCAL_2020-8-24-T144712\XML_LOCAL\QC_5b592411-0d27-4d2d-9cba-ce669a767645.xml
- OUT_CSW_URL =

Readers:
- TEXTLINE_1: TEXTLINE from $(IN_XML_FILE)

text_line (reader TEXTLINE_1)
    attributes: text_line_data buffer
    -> AttributeCreator_3
Note: Transfering CSW_URL in attribute
AttributeCreator_3
    ATTR_TABLE = SET_TO csw_url = $(OUT_CSW_URL)
    -> StringReplacer
Note: Removing Header
StringReplacer
    CASE = NO
    FIND_TEXT = <?xml version="1.0" encoding="UTF-8"?>
    NO_MATCH = _FME_NO_OP_
    REGEXP = NO
    SRC_ATTRS = text_line_data
    -> AttributeCreator_2
Note: Adding Transaction tag for PyCSW
AttributeCreator_2
    ATTR_TABLE:
      SET_TO _xml_data = <Transaction xmlns="http://www.opengis.net/cat/csw/2.0.2" version="2.0.2" service="CSW" xsi:schemaLocation="http://www.opengis.net/cat/csw/2.0.2 http://schemas.opengis.net/csw/2.0.2/CSW-publication.xsd                        http://www.isotc211.org/2005/gmd http://schemas.opengis.net/iso/19139/20070417/gmd/metadataEntity.xsd">
        <Insert>
        @Value(text_line_data)
        </Insert>
        </Transaction>
    -> XMLTemplater [ROOT]
Note: Adding XML Header
XMLTemplater
    OUTPUT_XML_HEADER = Yes
    RESULT_ATTRIBUTE = _xml_data
    ROOT_QUERY_EXPR = @Value(_xml_data)
    VISIBLE_QUERY_VALIDATE = Yes
    -> XMLFormatter_2
Note: Cleans up XML documents
XMLFormatter_2
    COLLAPSE_EMPTY_ELEMENT = No
    FORMATTING_CHOICE = Pretty-Print XML
    LIST_NAME = _xml_error
    NAMESPACE_CLEANUP = No
    SCHEMALOC_CLEANUP = No
    XML_ATTR_TEXT = _xml_data
    XML_INPUT_TYPE = Attribute Specifying XML Text
    XML_OUTPUT_ATTR = _xml_data
    XML_OUTPUT_TYPE = Attribute
    PASSED -> XMLValidator_2
Note: Validates XML syntax
XMLValidator_2
    LIMIT_ERRORS = No
    LIST_NAME = _xml_error
    VAL_MODE_1 = Syntax Only
    XML_ATTR_TEXT = _xml_data
    XML_INPUT_TYPE = Attribute Specifying XML Text
    PASSED -> PyCSW_POST_1
Note: Python script to insert XML to CSW
PyCSW_POST_1: PythonCaller
    NEW_ATTRIBUTES = insert_response
    PYTHONSOURCE:
      import fme
      import fmeobjects
      import urllib3
      import requests

      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):

          def __init__(self):
              pass



          def input(self,feature):
              try:
                  self.xml_str = feature.getAttribute('_xml_data')
                  self.xml_str = self.xml_str.encode('utf-8')
                  self.csw_url= feature.getAttribute('csw_url')

                  request_str = self.post_xml()

                  feature.setAttribute('insert_response', request_str)
              except:
                  feature.setAttribute('insert_response', 'error')

              self.pyoutput(feature)

          def post_xml(self):
              headers = {'Content-Type': 'text/xml; charset=utf-8'} # set what your server accepts

              return requests.post(self.csw_url, data=self.xml_str, headers=headers).text

          def close(self):
              pass
    PYTHONSYMBOL = FeatureProcessor
    -> Tester
Tester
    BOOL_OP = OR
    COMPOSITE_TEST = 1
    TEST_CLAUSE = TEST @Value(insert_response) != error
    TEST_MODE = TEST
    PASSED -> Tester_Passed
    FAILED -> Terminator
Tester_Passed: Logger
    LOG_FEATURE = LOG_ONLY
    MAXCOORDS = 20
    MAXFEATS = 20
    MESSAGE = Feature is:
    SEVERITY = INFO
Terminator
    MESSAGE = Translation Terminated
