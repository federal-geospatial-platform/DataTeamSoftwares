FME workspace SupprimerMetaPyCSW.fmw

Parameters:
- UUID_TO_DELETE = ALL   # ALL UUID_TO_DELETE
- CSW_URL = https://pycsw-bc.ddr-dev.cgp-pgc.ca/pycsw?
- LOG_FILE = C:\Users\ngariepy\Downloads\test.log   # Log File

Creator
    GEOMTYPE = Geometry Object
    NUM = 1
    CREATED -> Tester
Tester
    BOOL_OP = OR
    COMPOSITE_TEST = 1
    TEST_CLAUSE = TEST $(UUID_TO_DELETE) = ALL
    TEST_MODE = TEST
    PASSED -> Catalogue_Reader
    FAILED -> AttributeCreator
Catalogue_Reader: Catalogue Reader
    CUSTOM_CSW_LIST_NAME = MD_Metadata{}
    CUSTOM_CSW_SCHEMA = http://www.isotc211.org/2005/gmd
    CUSTOM_CSW_VERSION = 2.0.2
    CUSTOM_URL = $(CSW_URL)
    CUSTOM_URL_CSW_TYPENAMES = gmd:MD_Metadata
    SOURCE_URL = Manuel
    Résultats -> AttributeExposer
AttributeExposer
    ATTR_LIST = MD_Metadata.fileIdentifier.CharacterString
    -> FeatureHolder
FeatureHolder
    -> XMLTemplater_2
AttributeCreator
    ATTR_TABLE = SET_TO MD_Metadata.fileIdentifier.CharacterString = $(UUID_TO_DELETE)
    -> XMLTemplater_2
Note: Loads the Delete Records XML template for each CSW Data Record not found in the current data search
XMLTemplater_2
    QUERY_EXPR:
      <csw:Transaction xmlns:csw="http://www.opengis.net/cat/csw/2.0.2" xmlns:ogc="http://www.opengis.net/ogc" xmlns:apiso="http://www.opengis.net/cat/csw/apiso/1.0" xmlns:xsi="http://www.w3.org/2001/XMLSchema-instance" service="CSW" version="2.0.2" xsi:schemaLocation="http://www.opengis.net/cat/csw/2.0.2 http://schemas.opengis.net/csw/2.0.2/CSW-publication.xsd">
          <csw:Delete>
              <csw:Constraint version="1.1.0">
                  <ogc:Filter>
                      <ogc:PropertyIsLike escapeChar="\" singleChar="?" wildCard="*">
                          <ogc:PropertyName>dc:identifier</ogc:PropertyName>
                          <ogc:Literal>{fme:get-attribute("MD_Metadata.fileIdentifier.CharacterString")}</ogc:Literal>
                      </ogc:PropertyIsLike>
                  </ogc:Filter>
              </csw:Constraint>
          </csw:Delete>
      </csw:Transaction>
    RESULT_ATTRIBUTE = CSWRequest
    XQUERY_TYPE = Expression
    -> XMLFormatter_4
Note: Formats Delete Records XML's
XMLFormatter_4
    COLLAPSE_EMPTY_ELEMENT = No
    FORMATTING_CHOICE = Pretty-Print XML
    LIST_NAME = _xml_error
    NAMESPACE_CLEANUP = Yes
    SCHEMALOC_CLEANUP = Yes
    XML_ATTR_TEXT = CSWRequest
    XML_INPUT_TYPE = Attribute Specifying XML Text
    XML_OUTPUT_ATTR = _xml_output
    XML_OUTPUT_TYPE = Attribute
    PASSED -> XMLValidator_4
Note: Validates Delete Records XML's
XMLValidator_4
    LIMIT_ERRORS = No
    LIST_NAME = _xml_error
    VAL_MODE_1 = Syntax Only
    XML_ATTR_TEXT = CSWRequest
    XML_INPUT_TYPE = Attribute Specifying XML Text
    PASSED -> PyCSW_POST_4
Note: Posts Delete Records XML for each UUID in the CSW not found in the current data search, removing the obsolete record
PyCSW_POST_4: PythonCaller
    NEW_ATTRIBUTES = insert_response
    PYTHONSOURCE:
      import fme
      import fmeobjects
      import urllib3
      import requests

      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):

          def __init__(self):
              pass

              self.csw_url = fme.macroValues['CSW_URL']

          def input(self,feature):
              self.xml_str = feature.getAttribute('_xml_output')
              self.xml_str = self.xml_str.encode('utf-8')

              request_str = self.post_xml()

              feature.setAttribute('insert_response', request_str)

              self.pyoutput(feature)

          def post_xml(self):
              headers = {'Content-Type': 'text/xml; charset=utf-8'} # set what your server accepts

              return requests.post(self.csw_url, data=self.xml_str, headers=headers).text

          def close(self):
              pass
    PYTHONSYMBOL = FeatureProcessor
    -> Tester_2
Tester_2
    BOOL_OP = OR
    COMPOSITE_TEST = 1
    TEST_CLAUSE = TEST @Value(insert_response) != error
    TEST_MODE = TEST
