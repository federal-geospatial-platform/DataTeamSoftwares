FME workspace PrototypeGestionCourriel.fmw

SQLCreator
    DATASET = $(FME_MF_DIR_ENCODED)ValidationBrokenLinks.db
    EXPOSED_ATTRIBUTE_LIST = METADATA_UUID,URL,BROKEN_LINK_STATUS_DATE,BROKEN_LINK_STATUS
    FORMAT = SQLITE3
    SQLITE3_QUERY_FEATURE_TYPES_FOR_MERGE_FILTERS = Yes
    SQLITE3_SUPPORT_INTERNATIONALIZATION = YES
    SQL_STATEMENT = SELECT * FROM BROKEN_LINKS WHERE BROKEN_LINK_STATUS='CONFIRMED' AND EMAIL_STATUS='TO_DO'
    RESULT -> IdentificateurCourriel [Sampler_Input]
SQLExecutor
    COMBINE_ATTRS = Result Attributes Only
    COMBINE_GEOM = Initiator Geometry Only
    DATASET = $(FME_MF_DIR_ENCODED)ValidationBrokenLinks.db
    FORMAT = SQLITE3
    SQLITE3_QUERY_FEATURE_TYPES_FOR_MERGE_FILTERS = Yes
    SQLITE3_SUPPORT_INTERNATIONALIZATION = YES
    SQL_STATEMENT = UPDATE BROKEN_LINKS SET EMAIL_STATUS='DONE' WHERE METADATA_UUID='@Value(METADATA_UUID)' AND URL='@Value(URL)' AND BROKEN_LINK_STATUS_DATE='@Value(BROKEN_LINK_STATUS_DATE)' AND BROKEN_LINK_STATUS='@Value(BROKEN_LINK_STATUS)'
    <REJECTED> -> SQLExecutor__Rejected_
SQLExecutor__Rejected_: Inspector

Bookmark: Identification à qui envoyer le courriel
Note: Envoie notifications admin , MAJ liste des courriels
IdentificateurCourriel
    EMAIL -> SQLExecutor [INITIATOR]

FME custom transformer IdentificateurCourriel

Sampler_Input (input)
    -> Sampler
Sampler
    RATE = 2
    SAMPLE_MODE = No
    SAMPLE_TYPE_LONG = Every Nth Feature
    SAMPLED -> EMAIL (output)
    NOT_SAMPLED -> NO_EMAIL (output)
EMAIL (output)
NO_EMAIL (output)
